' script for Rhinoceros 3.0 Sr3
' generate a rib archive with RiBlobby information from objects generated by RandomBubbles Script
' exporter script
' © 2004 Clement Greiner

' update 9/21/2004 : fixed allocation of plane DBO inside output dir ("dbo_plane.dll")

Option Explicit

Sub RiBlobbyExporter
' RandomBubbles searching
Dim arrAllObjs, StrObject, arrSpheres()
Dim arrSegments(), arrStart, arrEnd
Dim arrPlanes(), dblStrength
Dim BubbleCount, SegCount, PlaneCount, StrValue
Dim dblRadius, arrCenter, StrCenter
' rib archive creation
Dim Index, StrPath, fsArchive, MyArchive, StrHeader, StrCode, StrMatrix(3), nCount
Dim intRiInfluence, POSCount, NEGCount, StrPOSCode, StrNEGCode, StrOperation
' color assignments
Dim lngColor, R, G, B

' Userdata from setup script
Dim StrArchivePath, msg
Dim intPrintProgress
Dim intAnnotate, StrAnn
Dim intSmooth
Dim intVertexColors, intInvertEColor, intInvertSColor, intInvertPColor
Dim intClipping
Dim intAllocatePlaneDBO, blnFound, EMsg
Dim intLCID

' set the current locale to en-us to force usage of the comma seperator "."
intLCID = Rhino.LocaleID
SetLocale("en-us")

' print commmand line progress option, default = on
intPrintProgress = Rhino.GetDocumentData("RiBlobbyExporter", "PrintProgress")
If IsNull(intPrintProgress) Then intPrintProgress = 1
' include annotations, default = off
intAnnotate = Rhino.GetDocumentData("RiBlobbyExporter", "IncludeAnnotation")
If IsNull(intAnnotate) Then intAnnotate = 0
' add (ShadingInterpolation "Smooth") to archive, default = no
intSmooth = Rhino.GetDocumentData("RiBlobbyExporter", "ShadingSmooth")
If IsNull(intSmooth) Then intSmooth = 0
' get all selectable objects
If intPrintProgress = 1 Then Rhino.Print "Searching for Bubble objects..."
' invert color for negative objects
intInvertEColor = Rhino.GetDocumentData("RiBlobbyExporter", "Invert1001")
If IsNull(intInvertEColor) Then intInvertEColor = 1
intInvertSColor = Rhino.GetDocumentData("RiBlobbyExporter", "Invert1002")
If IsNull(intInvertSColor) Then intInvertSColor = 1
intInvertPColor = Rhino.GetDocumentData("RiBlobbyExporter", "Invert9000")
If IsNull(intInvertPColor) Then intInvertPColor = 1
' clipping plane adjustment (add 2 point objects before export)
intClipping = Rhino.GetDocumentData("RiBlobbyExporter", "AdjustClipping")
If IsNull(intClipping) Then intClipping = 1
' auto render after export is done / default = 1
If IsNull(Rhino.GetDocumentData("RiBlobbyExporter", "Render")) Then Rhino.SetDocumentData "RiBlobbyExporter", "Render", 1

' include all selectable RiObjects
arrAllObjs = Rhino.NormalObjects
If Not IsArray(arrAllObjs) Then Rhino.Print "No Objects found in this document to process." : Exit Sub
' status bar info
Rhino.StatusBarMessage "Reading Blobby primitives: "

' search for "RandomBubbles" objects with 1001,1002,9000 user data
BubbleCount = 0 : SegCount = 0 : PlaneCount = 0
For Each StrObject In arrAllObjs
	StrValue = Rhino.GetObjectData(StrObject, "RandomBubbles", "RiOpcode")
		' if the object has 1001 opcode, add to arrSpheres
		If StrValue = "1001" Then
			Redim Preserve arrSpheres(BubbleCount)
			arrSpheres(BubbleCount) = StrObject
			BubbleCount = BubbleCount + 1
		' if the object has 1002 opcode, add to arrSegments
		ElseIf StrValue = "1002" Then
			Redim Preserve arrSegments(SegCount)
			arrSegments(SegCount) = StrObject
			SegCount = SegCount + 1
		' if the object has 9000 opcode, add to arrPlanes
		ElseIf StrValue = "9000" Then
			Redim Preserve arrPlanes(PlaneCount)
			arrPlanes(PlaneCount) = StrObject
			PlaneCount = PlaneCount + 1
		End If
		Rhino.StatusBarMessage "Reading Blobby primitives: " & BubbleCount + SegCount + PlaneCount
Next
' print
If intPrintProgress = 1 Then
	If BubbleCount > 0 Then Print "Number of 1001 (ellipsoids) found: " & BubbleCount
	If SegCount > 0 Then Print "Number of 1002 (segments) found: " & SegCount
	If PlaneCount > 0 Then Print "Number of 9000 (planes) found: " & PlaneCount
End If

' process bubbles or exit
If BubbleCount + SegCount + PlaneCount > 0 Then
	Rhino.Print "Number of RiBlobby Objects to process: " & BubbleCount + SegCount + PlaneCount & " ....press ESC to cancel"
Else
	Rhino.Print "No RiBlobby objects (ellipsoid, segment or plane) found in this document to export."
	Exit Sub
End If

' #######################################################################
' #############  		write blobby archive.rib		#################
' #######################################################################

' if the exporter setup was not started, define a default output path now
StrArchivePath = Rhino.GetDocumentData("RiBlobbyExporter", "ArchivePath")
If IsNull(StrArchivePath) Or StrArchivePath = "ERROR" Then
   ' if not specified, read from registry
	StrArchivePath = GET_RhinoManDefaultPath
	If StrArchivePath = "ERROR" Then
		' manually define a path
		msg = "Select a destination folder to create RiBlobby file " & CHR(34) & "MyArchive.rib" & CHR(34)
    	StrArchivePath = Rhino.BrowseForFolder( , msg , "OutputFolder" )
        	If IsNull(StrArchivePath) Then
        		Rhino.Print "Error line 106 - Command aborted. No output path defined."
        		Exit Sub
        	Else
            	Rhino.Print "Default RiBlobby output folder has been set to : " & CHR(34) & StrArchivePath & CHR(34)
        	End If
	End If
	' use this path as new default path, re-enable this setting
    Rhino.SetDocumentData "RiBlobbyExporter", "UseDefaultPath", 1
    ' store the path
    Rhino.SetDocumentData "RiBlobbyExporter", "ArchivePath", StrArchivePath
End If

' read destination path from document (setup)
StrPath = Rhino.GetDocumentData("RiBlobbyExporter", "ArchivePath")
If IsNull(StrPath) Then Rhino.Print "Output path not found, command aborted." : Exit Sub

' !!!!!!!!!!!!!!!!!!!!!!!!!!!!!!!!!!!!!!!!!!!!!!!!!!!!!!!!!!!!!!!!!!!!!!!!!!!!!!!!!!!!!!!
StrPath = StrPath & "\"

' allocate the dbo_plane.dll DBO inside output path if plane (9000) objects where found and option is enabled
IntAllocatePlaneDBO = Rhino.GetDocumentData("RiBlobbyExporter", "AllocatePlaneDBO")
If PlaneCount > 0 And IntAllocatePlaneDBO = 1 Then
	blnFound = ReportFileStatus(StrPath & "dbo_plane.dll")
	If blnFound <> 1 Then
		EMsg = "The DBO file " & CHR(34) & "dbo_plane.dll" & CHR(34) & " was not found	  "
		EMsg = EMsg & vbNewLine & "inside your output path: " & CHR(34) & StrPath & CHR(34)
		EMsg = EMsg & vbNewLine & vbNewLine & "To avoid this error, copy the dbo_plane from"
		EMsg = EMsg & vbNewLine & "AIR directory to your output path location,"
		EMsg = EMsg & vbNewline & "or define the Searchpath for procedurals :"
		EMsg = EMsg & vbNewLine & vbNewLine & "RhinoOptions > RhinoMan > SearchPaths"
		MsgBox EMSg , 64 , "DBO searcher"
		Exit Sub
	End If
End If

If intPrintProgress = 1 Then Print "Writing RiBlobby archive to " & CHR(34) & StrPath & "MyArchive.rib" & CHR(34)

Set fsArchive = CreateObject("Scripting.FileSystemObject")
Set MyArchive = fsArchive.CreateTextFile(StrPath & "MyArchive.rib", True)

' writing the archive header inside this rib
StrHeader = GET_ArchiveHeader(intSmooth) : MyArchive.WriteLine(CStr(StrHeader))

' Write in the number of Blobbys (array count) and starting "["
StrCode = "Blobby " & Int(BubbleCount + SegCount + PlaneCount) & vbNewLine & "["
MyArchive.WriteLine(CStr(StrCode))

' #######################################################################
' ####    Write the leaf codes (1001 0 	1001 16 	1001 32 ....)     ###
' #######################################################################

For Index = 0 To BubbleCount-1
	' form 1001 (index*16)
	If IntAnnotate = 1 Then StrAnn = CStr(vbTab & vbTab & vbTab & "#" & Index & " sphere") Else StrAnn = ""
	StrCode = "1001 " & Int(Index * 16) & StrAnn
	MyArchive.WriteLine(CStr(StrCode))
	Rhino.StatusBarMessage "Writing Opcode 1001 geometry: " & index + 1
Next
' write 1002 (segment) leaf codes (1002 0 	1002 23 	1002 46 ....)
For Index = 0 To SegCount-1
	' form 1002 (index*23)
	If IntAnnotate = 1 Then StrAnn = CStr(vbTab & vbTab & vbTab & "#" & Index + BubbleCount & " segment") Else StrAnn = ""
	StrCode = "1002 " & (BubbleCount*16)+(index*23) & StrAnn
	MyArchive.WriteLine(CStr(StrCode))
	Rhino.StatusBarMessage "Writing Opcode 1002 geometry: " & index + 1
Next
' write 9000 (plane) leaf codes (eg: 9000 4 0 16 1 32 .... 9000 4 0 33 1 49 ...)
For Index = 0 To PlaneCount-1
	' form 9000 4 0 indexstart floatstrength(1) indexend
	StrCode = "9000 4 0 " & (BubbleCount*16)+(SegCount*23)+(Index*16)+Index & " 1 " & (BubbleCount*16)+(SegCount*23)+(Index*16) + 16 + Index
	If IntAnnotate = 1 Then StrAnn = CStr(vbTab & "#" & Index + BubbleCount + SegCount & " plane") Else StrAnn = ""
	MyArchive.WriteLine(CStr(StrCode & StrAnn))
	Rhino.StatusBarMessage "Writing Opcode 9000 geometry: " & index + 1
Next

' #######################################################################


' search / count 1001 spheres with positive and negative influence assignments
POSCount = 0 : NEGCount = 0
For Each StrObject In arrSpheres
	' get the RiInfluence value
	intRiInfluence = Int(Rhino.GetObjectData(StrObject, "RandomBubbles", "RiInfluence"))
	If intRiInfluence = 1 Then POSCount = POSCount + 1
	If intRiInfluence = -1 Then NEGCount = NEGCount + 1
	Rhino.StatusBarMessage "Reading 1001 influence modes: (" & POSCount & "/" & NEGCount & ")"
Next
' search / count 1002 segments with positive and negative influence assignments
For Each StrObject In arrSegments
	' get the RiInfluence value
	intRiInfluence = int(Rhino.GetObjectData(StrObject, "RandomBubbles", "RiInfluence"))
	If intRiInfluence = 1 Then POSCount = POSCount + 1
	If intRiInfluence = -1 Then NEGCount = NEGCount + 1
	Rhino.StatusBarMessage "Reading 1002 influence modes: (" & POSCount & "/" & NEGCount & ")"
Next
' search / count 9000 planes with positive and negative influence assignments
For Each StrObject In arrPlanes
	' get the RiInfluence value
	intRiInfluence = int(Rhino.GetObjectData(StrObject, "RandomBubbles", "RiInfluence"))
	If intRiInfluence = 1 Then POSCount = POSCount + 1
	If intRiInfluence = -1 Then NEGCount = NEGCount + 1
	Rhino.StatusBarMessage "Reading 9000 influence modes: (" & POSCount & "/" & NEGCount & ")"
Next
If intPrintProgress = 1 Then Print "Found " & POSCount & " positive RiBlobby objects, " & NEGCount & " negative RiBlobby objects."

' do something if error occured, decide to union all or subtract (POS-NEG)
If (POSCount+NEGCount) <> BubbleCount + SegCount + PlaneCount Then MsgBox "Error - line 108" : Exit Sub
' define operation (1 = All Positive, 2 = Positive & Negative)
If POSCount = (BubbleCount+SegCount+PlaneCount) Or NEGCount = (BubbleCount+SegCount+PlaneCount) Then
	' Print "Only positive OR negative objects found."
	StrOperation = "Union"
ElseIf NEGCount <> 0 And (POSCount+NEGCount) = BubbleCount+SegCount+PlaneCount Then
	' Print "positive AND negative objects found."
	StrOperation = "Subtract"
End If

If intPrintProgress = 1 Then Print StrOperation

' ########################## union all ##########################

' union all spheres
If StrOperation = "Union" Then
	Rhino.StatusBarMessage "Writing UNION data..."
	' Write in the add code (add mode = (0) at first position then count = (7) ... 0 1 2 3 4 5 6)
	StrCode = "0 " & BubbleCount+SegCount+PlaneCount '(addmode=0 & (SphereCount + SegmentCount + PlaneCount)
	' array for all 1001 objs
	For Index = 0 To BubbleCount-1 : StrCode = StrCode & " " & Index : Next
	' array for all 1002 objs
	For Index = 0 To SegCount-1 : StrCode = StrCode & " " & (BubbleCount+ Index) : Next
	' array for all 9000 objs
	For Index = 0 To PlaneCount-1 : StrCode = StrCode & " " & (BubbleCount+SegCount+Index) : Next
	' write add code ( (Add=0 | count | array of positive objects)
	MyArchive.WriteLine(CStr(StrCode))
End If

' ########################## subtract (POS-NEG) ##########################

' add all POS spheres, add all NEG spheres, Subtract > POS - NEG = result
nCount = 0
If StrOperation = "Subtract" Then
	Rhino.StatusBarMessage "Writing Union/Subtraction data..."
	' add ("0") all positives
	StrPOSCode = "0 " & POSCount
	' add or group negatives (setup)
	If int(Rhino.GetDocumentData("RiBlobbyExporter","AddSubtractors")) = 1 Then StrNEGCode = "0 " & NEGCount Else StrNEGCode = "2 " & NEGCount
	' add / sub 1001 spheres
	For Index = 0 To BubbleCount-1
		intRiInfluence = int(Rhino.GetObjectData(arrSpheres(index), "RandomBubbles", "RiInfluence"))
		If intRiInfluence = 1 Then StrPOSCode = StrPOSCode & " " & Index
		If intRiInfluence = -1 Then StrNEGCode = StrNEGCode & " " & Index
		'nCount = nCount + 1
	Next
	' add / sub 1002 segementd
	For Index = 0 To SegCount-1
	intRiInfluence = int(Rhino.GetObjectData(arrSegments(index), "RandomBubbles", "RiInfluence"))
		If intRiInfluence = 1 Then StrPOSCode = StrPOSCode & " " & (Index + BubbleCount)
		If intRiInfluence = -1 Then StrNEGCode = StrNEGCode & " " & (Index + BubbleCount)
		'nCount = nCount + 1
	Next
	' add / sub 9000 planes
	For Index = 0 To PlaneCount-1
	intRiInfluence = int(Rhino.GetObjectData(arrPlanes(index), "RandomBubbles", "RiInfluence"))
		If intRiInfluence = 1 Then StrPOSCode = StrPOSCode & " " & (Index + BubbleCount + SegCount)
		If intRiInfluence = -1 Then StrNEGCode = StrNEGCode & " " & (Index + BubbleCount+ SegCount)
		'ncount = ncount + 1
	Next

	' write add code for positive objects
	MyArchive.WriteLine(CStr(StrPOSCode))
	' write add code for negative objects
	MyArchive.WriteLine(CStr(StrNEGCode))

	' subtract ("4") negative from positive objects
	If IntAnnotate = 1 Then StrAnn = " # Subract POS-NEG" Else StrAnn = ""
	StrCode = "4 " & (BubbleCount+SegCount+PlaneCount) & " " & (BubbleCount+SegCount+PlaneCount+1) & StrAnn
	MyArchive.WriteLine(CStr(StrCode))
End If

' end of machine code ("]")
MyArchive.WriteLine(CStr("]"))

' #######################################################################################################
' ####################################  Coordiante float generation  ####################################
' #######################################################################################################

' start machine code
If intPrintProgress = 1 Then Print "Writing RiBlobby coordinates for " & (BubbleCount+SegCount+PlaneCount) & " objects ... please wait"
MyArchive.WriteLine(CStr("["))

' create the fucking machine code for all 1001 spheres
ncount = 0 : StrCode = ""
For Each StrObject In arrSpheres
	' Write 1001 spheres / read in the radius and center pt
	If Rhino.IsPoint(StrObject) Then
		dblRadius = 2 * Round(CStr(Rhino.GetObjectData(StrObject,"RandomBubbles","Radius")),6)
		arrCenter = Rhino.PointCoordinates(StrObject)
		' create 4x4 Point matrix (16 points) > (r 0 0 0		0 r 0 0		0 0 r 0		x y z 1)
		StrMatrix(0) = dblRadius & " 0 0 0"
		StrMatrix(1) = "0 " & dblRadius & " 0 0"
		StrMatrix(2) = "0 0 " & dblRadius & " 0"
		StrMatrix(3) = Round(arrCenter(0),6) & " " & Round(arrCenter(1),6) & " " & Round(arrCenter(2),6) & " " & "1"
		If IntAnnotate = 1 Then StrAnn = CStr(vbTab & "#" & nCount) Else StrAnn = ""
		StrCode = StrMatrix(0) & vbTab & StrMatrix(1) & vbTab & StrMatrix(2) & vbTab & StrMatrix(3) & StrAnn
	Else
		' if a sphere or ellipsoid (1001) object is found
		If IntAnnotate = 1 Then StrAnn = CStr(vbTab & "#" & nCount) Else StrAnn = ""
		StrCode = GET_EllipsoidMatrix(StrObject) & StrAnn
	End If
	'Write the 16 floats per sphere in one row
	MyArchive.WriteLine(CStr(StrCode))
	nCount = nCount + 1
	Rhino.StatusBarMessage "Writing primitives: " & nCount
Next

StrCode = ""
' create the f... code for all 1002 segments
For Each StrObject In arrSegments
	' Write polyline a 1002 segment / read in the radius and start/end pt
	If Rhino.IsPolyline(StrObject) Then
		dblRadius = Rhino.GetObjectData(StrObject,"RandomBubbles","Radius")
		arrStart = Rhino.CurveStartPoint(StrObject)
		arrEnd = Rhino.CurveEndPoint(StrObject)
		StrMatrix(0) = Round(arrStart(0),6) & " " & Round(arrStart(1),6) & " " & Round(arrStart(2),6)
		StrMatrix(1) = Round(arrEnd(0),6) & " " & Round(arrEnd(1),6) & " " & Round(arrEnd(2),6)
		StrMatrix(2) = 2*dblRadius
		StrMatrix(3) = "1 0 0 0 0 1 0 0 0 0 1 0 0 0 0 1"
		' create startpt(x,y,z) | endpt(x,y,z) | radius | 4*4 Matrix
		If IntAnnotate = 1 Then StrAnn = CStr(vbTab & "#" & nCount) Else StrAnn = ""
		StrCode = StrMatrix(0) & vbTab & StrMatrix(1) & vbTab & StrMatrix(2) & vbTab & StrMatrix(3) & StrAnn
	Else
		' if 1002 segment object (surface) is found
		If IntAnnotate = 1 Then StrAnn = CStr(vbTab & "#" & nCount) Else StrAnn = ""
		StrCode = GET_SegmentMatrix(StrObject) & StrAnn
	End If
	'Write the 23 floats per segment in one row
	MyArchive.WriteLine(CStr(StrCode))
	nCount = nCount + 1
	Rhino.StatusBarMessage "Writing primitives: " & nCount
Next

StrCode = ""
' create code for all 9000 planes
For Each StrObject In arrPlanes
	' write Plane 4x4 matrix and strength value
		StrCode = GET_PlaneMatrix(StrObject)
		If IntAnnotate = 1 Then StrAnn = CStr(vbTab & "#" & nCount) Else StrAnn = ""
		MyArchive.WriteLine(CStr(StrCode & StrAnn))
		nCount = nCount + 1
		Rhino.StatusBarMessage "Writing primitives: " & nCount
Next

' end of machine code
MyArchive.WriteLine(CStr("]"))

' add list(0) of plane stings [""]
If PlaneCount = 0 Then
	StrCode = "[" & CHR(34) & CHR(34) & "]"
Else
	StrCode = "[" & CHR(34) & "dbo_plane" & CHR(34) & "]"
End If
MyArchive.WriteLine(CStr(StrCode))

' ##############################################################################
' #######################       add Vertex colors       ########################
' ##############################################################################

IntVertexColors = Rhino.GetDocumentData("RiBlobbyExporter", "VertexColors")
If IsNull(IntVertexColors) Then IntVertexColors = 0
If IntVertexColors = 1 Then

    If intPrintProgress = 1 Then Print "assigning vertex colors to " & (BubbleCount+SegCount+PlaneCount) & " objects"

    StrCode = CHR(34) & "varying color Cs"  & CHR(34) & " ["
    MyArchive.WriteLine(CStr(StrCode))

    ' get object wireframe or material colors (1001) and write as vertex color
    nCount = 0
    For Each StrObject In arrSpheres
        lngColor = Rhino.ObjectColor(StrObject)
        R = GetRValue(lngColor) : G = GetGValue(lngColor) : B = GetBValue(lngColor)
        R = CONVERT_Digits(R/255) : G = CONVERT_Digits(G/255) : B = CONVERT_Digits(B/255)
        If IntAnnotate = 1 Then StrAnn = CStr(vbTab & vbTab & "#" & nCount) Else StrAnn = ""
        If intInvertEColor = 0 Or StrOperation = "Union" Then
        	StrCode = R & " " & G & " " & B & StrAnn
        Else
            StrCode = CStr(GET_InvertNegativeColor(StrObject,R,G,B) & StrAnn)
        End If
        MyArchive.WriteLine(CStr(StrCode))
        nCount = nCount + 1
        Rhino.StatusBarMessage "Writing vertex colors: " & nCount
    Next
    If intPrintProgress = 1 Then
    	If BubbleCount > 0 Then Print "Writing " & nCount & " vertex colors for 1001 spheres"
    End If
    ' get the wireframe or material colors (1002) and write as vertex color
    For Each StrObject In arrSegments
        lngColor = Rhino.ObjectColor(StrObject)
        R = GetRValue(lngColor) : G = GetGValue(lngColor) : B = GetBValue(lngColor)
        R = CONVERT_Digits(R/255) : G = CONVERT_Digits(G/255) : B = CONVERT_Digits(B/255)
        If IntAnnotate = 1 Then StrAnn = CStr(vbTab & vbTab & "#" & nCount) Else StrAnn = ""
        If intInvertSColor = 0 Or StrOperation = "Union" Then
        	StrCode = R & " " & G & " " & B & StrAnn
        Else
            StrCode = CStr(GET_InvertNegativeColor(StrObject,R,G,B) & StrAnn)
        End If
        MyArchive.WriteLine(CStr(StrCode))
        nCount = nCount + 1
        Rhino.StatusBarMessage "Writing vertex colors: " & nCount
    Next
    If intPrintProgress = 1 Then
    	If SegCount > 0 Then Print "Writing " & SegCount & " vertex colors for 1002 segments"
    End If
    ' get the wireframe or material colors (1002) and write as vertex color
    For Each StrObject In arrPlanes
        lngColor = Rhino.ObjectColor(StrObject)
        R = GetRValue(lngColor) : G = GetGValue(lngColor) : B = GetBValue(lngColor)
        R = CONVERT_Digits(R/255) : G = CONVERT_Digits(G/255) : B = CONVERT_Digits(B/255)
        If IntAnnotate = 1 Then StrAnn = CStr(vbTab & vbTab & "#" & nCount) Else StrAnn = ""
        If intInvertPColor = 0 Or StrOperation = "Union" Then
        	StrCode = R & " " & G & " " & B & StrAnn
        Else
            StrCode = CStr(GET_InvertNegativeColor(StrObject,R,G,B) & StrAnn)
        End If
        MyArchive.WriteLine(CStr(StrCode))
        nCount = nCount + 1
        Rhino.StatusBarMessage "Writing vertex colors: " & nCount
    Next
    If intPrintProgress = 1 Then
    	If PlaneCount > 0 Then Print "Writing " & PlaneCount & " vertex colors for 9000 plane DBOs"
    End If

    ' close vertex color
    MyArchive.WriteLine(CStr("]"))

' end if vertexcolors
End If
' ##############################################################################

' close the rib attribute
StrCode = "AttributeEnd" & vbNewLine & "AttributeEnd"
MyArchive.WriteLine(CStr(StrCode))

Rhino.StatusBarMessage "Closing archive..."

' close the archive file
MyArchive.Close
Set fsArchive = Nothing

' open the archive file with air control
'Rhino.Command "Run " & StrPath & "MyArchive.rib"

' start the auto rendering if enabled in setup
If Int(Rhino.GetDocumentData("RiBlobbyExporter", "Render")) = 1 Then START_Render BubbleCount,SegCount,PlaneCount,arrSpheres,arrSegments,arrPlanes,intClipping
' exit
Rhino.Print "Exporter Ready."
Rhino.StatusbarMessage "Done."

' reset locale
SetLocale(intLCID)

End Sub

' function to read the rhinoman path from registry
Private Function GET_RhinoManDefaultPath
Dim Sh, key, a
On Error Resume Next
Set Sh = CreateObject("WScript.Shell")
key = "HKEY_CURRENT_USER\Software\McNeel\Rhinoceros\3.0\Scheme: Default\Plug-ins\0AC6FEA5-68A5-4856-8677-6AF9C3E99C3A\Settings\OutputPath"
a = Sh.RegRead (key)
If Len(a) = 0 Then
	MsgBox "The registry key to read the RhinoMan default path cannot be found", vbOkOnly , "ReadDefaultPath"
	GET_RhinoManDefaultPath = "ERROR"
Else
	Rhino.Print "Reading RhinoMan default directory from registry : " & CHR(34) & a & CHR(34)
	GET_RhinoManDefaultPath = a
End If
Set Sh = Nothing
End Function

' function to allocate a file at a defined location
Function ReportFileStatus(StrFilePathName)
Dim Reportfso, IntReport
Set Reportfso = CreateObject("Scripting.FileSystemObject")
If (Reportfso.FileExists(StrFilePathName)) Then
   Print "Found file at: " & Chr(34) & StrFilePathName & Chr(34)
   IntReport = 1
Else
   Print "Error - " & Chr(34) & StrFilePathName & Chr(34) & " - file not found"
   IntReport = 0
End If
Set Reportfso = Nothing
ReportFileStatus = IntReport
End Function

' function to write the archive header
Private Function GET_ArchiveHeader(intSmooth)
Dim StrText
StrText = "#RandomBubbles RIB geometry archive"
StrText = StrText & vbNewLine & "#Version: 1.0"
StrText = Strtext & vbNewLine & "#CreationDate: " & Date
StrText = StrText & vbNewLine & "#Copyright(©) Clement Greiner, 2004"
StrText = StrText & vbNewLine & "AttributeBegin"
If intSmooth = 1 Then StrText = StrText & vbNewLine & "Attribute " & CHR(34) & "ShadingInterpolation" & CHR(34) & " " & CHR(34) & "smooth" & CHR(34)
StrText = StrText & vbNewLine & "AttributeBegin"
' return header
GET_ArchiveHeader = StrText
End Function

Private Function START_Render(BCount,SCount,PCount,arrSpheres,arrSegments,arrPlanes,intClipping)
Dim arrClipPts
Rhino.EnableRedraw(vbFalse)
' hide blobbies
If BCount > 0 Then Rhino.HideObjects arrSpheres
If SCount > 0 Then Rhino.HideObjects arrSegments
If PCount > 0 Then Rhino.HideObjects arrPlanes
' add clipping point objects if enabled
If intClipping = 1 Then arrClipPts = ADD_ClippingPoints
' render rhino scene
Rhino.Command "_Render", vbFalse
Rhino.Print "Render started..."
' delete clipping point objects
If intClipping = 1 Then Rhino.DeleteObjects arrClipPts
' show blobbies
If BCount > 0 Then Rhino.ShowObjects arrSpheres
If SCount > 0 Then Rhino.ShowObjects arrSegments
If PCount > 0 Then Rhino.ShowObjects arrPlanes
Rhino.EnableRedraw(vbTrue)
End Function

Private Function ADD_ClippingPoints
Dim arrCt, arrTemp, arrCPt, arrTPt, dblDistance, arrPtObjs(1)
arrCT = Rhino.ViewCameraTarget(CStr(Rhino.CurrentView))
dblDistance = Rhino.Distance(arrCt(0),arrCt(1))
arrTemp = Array(Rnd(10),Rnd(10),0)
arrCPt = Rhino.XFormCPlaneToWorld(Str2Pt(dblDistance * 0.1 & ",0,0"), Array(arrCT(0), arrCT(1), arrTemp))
arrTPt = Rhino.XFormCPlaneToWorld(Str2Pt(dblDistance * 2.0 & ",0,0"), Array(arrCT(0), arrCT(1), arrTemp))
arrPtObjs(0) = Rhino.AddPoint(arrCPt)
arrPtObjs(1) = Rhino.AddPoint(arrTPt)
ADD_ClippingPoints = arrPtObjs
End Function

' function to invert rgb values if object is negative
Private Function GET_InvertNegativeColor(StrObj,R,G,B)
Dim intInfluence, Rval, GVal, Bval
intInfluence = int(Rhino.GetObjectData(StrObj, "RandomBubbles", "RiInfluence"))
If intInfluence = 1 Then
	' return regular color value
	GET_InvertNegativeColor	= R & " " & G & " " & B
	Exit Function
Else
	If R = 1 Then
		Rval = "0.000"
	ElseIf R = 0 Then
		Rval = "1.000"
	Else
		Rval = 1-R
	End If
	If G = 1 Then
		Gval = "0.000"
	ElseIf G = 0 Then
		Gval = "1.000"
	Else
		Gval = 1-G
	End If
	If B = 1 Then
		Bval = "0.000"
	ElseIf B = 0 Then
		Bval = "1.000"
	Else
		Bval = 1-B
	End If
	' return inverted color value
	GET_InvertNegativeColor	= Rval & " " & Gval & " " & Bval
End If
End Function

' function to return red from lng color value
Public Function GetRValue (val)
If val > -1 And val < 16777216 Then
	GetRValue = val \ 256 ^ 0 And 255
Else
	GetRValue = -1
End If
End Function
' function to return green from lng color value
Public Function GetGValue (val)
If val > -1 And val < 16777216 Then
	GetGValue = val \ 256 ^ 1 And 255
Else
	GetGValue = -1
End If
End Function
' function to return blue from lng color value
Public Function GetBValue (val)
  If val > -1 And val < 16777216 Then
	GetBValue = val \ 256 ^ 2 And 255
Else
	GetBValue = -1
End If
End Function

' convert a renderman color value <=1 to (n)digits
Public Function CONVERT_Digits(val)
Dim IntDigits ' number of digits to output
IntDigits = 5
If val > 1 Then MsgBox "Error - CDColor - Dummy !" : Exit Function
If Len(val) = 1 Then
	CONVERT_Digits = val & "." & String(IntDigits-2,"0")
	Exit Function
ElseIf Len(val) = IntDigits Then
	CONVERT_Digits = val
	Exit Function
End If
If Left(Right(val,4),1) = "E" Then
	CONVERT_Digits = "0." & String(IntDigits-2,"0")
	Exit Function
ElseIf Len(val) < IntDigits Then
	CONVERT_Digits = val & String(IntDigits-Len(val),"0")
	Exit Function
ElseIf Len(val) > IntDigits Then
	Convert_Digits = Left(val,IntDigits)
	Exit Function
End If
End Function

' function to generate the 1001 matrix
Private Function GET_EllipsoidMatrix(StrObject)
Dim arrPts, X,Y,Z,XNeg, arrCenter, XAxis, YAxis, ZAxis
Dim arrTempX, arrTempY, arrTempZ, d, StrX, StrY, StrZ, StrC
' get all srfpoints, define extremes
arrPts = Rhino.SurfacePoints(StrObject)
X = arrPts(2) : Y = arrPts(12) : Z = arrPts(4) : XNeg = arrPts(22)
' calculate centerpoint from x, -x
arrCenter = Str2Pt(((X(0) + XNeg(0) ) / 2) & "," & ((X(1) + XNeg(1) ) / 2) & "," & ((X(2) + XNeg(2) ) / 2))
' define the transform axes (1 unit long)
XAxis = Rhino.XFormCPlaneToWorld(Array(1,0,0),Array(arrCenter,X,Y))
YAxis = Rhino.XFormCPlaneToWorld(Array(0,1,0),Array(arrCenter,X,Y))
ZAxis = Rhino.XFormCPlaneToWorld(Array(0,0,1),Array(arrCenter,X,Y))
' multiply axes (n * 2)
arrTempX = Rhino.XFormCPlaneToWorld( Array((2 * Rhino.Distance(arrCenter,X)),0,0), Array(arrCenter,XAxis,YAxis,ZAxis))
arrTempY = Rhino.XFormCPlaneToWorld( Array(0,(2 * Rhino.Distance(arrCenter,Y)),0), Array(arrCenter,XAxis,YAxis,ZAxis))
arrTempZ = Rhino.XFormCPlaneToWorld( Array(0,0,(2 * Rhino.Distance(arrCenter,Z))), Array(arrCenter,XAxis,YAxis,ZAxis))
'Subtract Center Point from axis points (make relative To center)
d = 4
StrX = Round(arrTempX(0)-arrCenter(0),d) & " " & Round(arrTempX(1)-arrCenter(1),d) & " " & Round(arrTempX(2)-arrCenter(2),d) & " 0"
StrY = Round(arrTempY(0)-arrCenter(0),d) & " " & Round(arrTempY(1)-arrCenter(1),d) & " " & Round(arrTempY(2)-arrCenter(2),d) & " 0"
StrZ = Round(arrTempZ(0)-arrCenter(0),d) & " " & Round(arrTempZ(1)-arrCenter(1),d) & " " & Round(arrTempZ(2)-arrCenter(2),d) & " 0"
StrC = Round(arrCenter(0),d) & " " & Round(arrCenter(1),d) & " " & Round(arrCenter(2),d) & " 1"
' return 4x4 matrix
GET_EllipsoidMatrix = StrX & vbTab & StrY & vbTab & StrZ & vbTab & StrC
End Function

' function to generate the 1002 matrix
Private Function GET_SegmentMatrix(StrObject)
Dim arrPts, arrS1, arrS2, arrE1, arrE2, d, StrStart, StrEnd
d = 5
' get srf points
arrPts = Rhino.SurfacePoints(StrObject)
' calculate segment start/end
arrS1=arrPts(2) : arrS2=arrPts(30) : arrE1=arrPts(4) : arrE2=arrPts(32)
' get mid points
StrStart = Round((arrS1(0)+arrS2(0))/2,d) & " " & Round((arrS1(1)+arrS2(1))/2,d) & " " & Round((arrS1(2)+arrS2(2))/2,d)
StrEnd = Round((arrE1(0)+arrE2(0))/2,d) & " " & Round((arrE1(1)+arrE2(1))/2,d) & " " & Round((arrE1(2)+arrE2(2))/2,d)
' return with radius
GET_SegmentMatrix = StrStart & vbTab & StrEnd & vbTab & Round(CStr(Rhino.Distance(arrS1,arrS2)),d) & vbTab & "1 0 0 0 0 1 0 0 0 0 1 0 0 0 0 1"
End Function

' function to generate the 9000 matrix
Private Function GET_PlaneMatrix(StrObject)
Dim arrPts, arrA, arrB, arrC, arrD, arrXDir, arrYDir, arrZDir, arrCenter, dblStrength
Dim arrParam, arrNormal, XAxis, YAxis, ZAxis, arrTempX, arrTempY, arrTempZ
Dim StrX, StrY, StrZ, StrC, d
dblStrength = Rhino.GetObjectData(StrObject,"RandomBubbles","PlaneStrength")
' get plane extremes
arrPts = Rhino.SurfacePoints(StrObject)
' define 4 points
arrA = arrPts(0) : arrB = arrPts(1) : arrC = arrPts(2) : arrD = arrPts(3)
' define the center point from the diagonal/2
arrCenter = Str2Pt((ArrA(0)+ArrD(0))/2 & "," & (ArrA(1)+ArrD(1))/2 & "," & (ArrA(2)+ArrD(2))/2)
' define the x y axis direction
arrXDir = Str2Pt((ArrC(0)+arrD(0))/2 & "," & (ArrC(1)+arrD(1))/2 & "," & (ArrC(2)+arrD(2))/2)
arrYDir = Str2Pt((ArrB(0)+arrD(0))/2 & "," & (ArrB(1)+arrD(1))/2 & "," & (ArrB(2)+arrD(2))/2)
' get z axis direction
arrParam = Rhino.SurfaceClosestPoint(StrObject, arrCenter)
arrNormal = Rhino.SurfaceNormal(StrObject, arrParam)
arrZDir = arrNormal(1)
' define the transform axes (1 unit long)
XAxis = Rhino.XFormCPlaneToWorld(Array(1,0,0),Array(arrCenter,arrXDir,arrYDir))
YAxis = Rhino.XFormCPlaneToWorld(Array(0,1,0),Array(arrCenter,arrXDir,arrYDir))
ZAxis = Rhino.XFormCPlaneToWorld(Array(0,0,1),Array(arrCenter,arrXDir,arrYDir))
' multiply xy axes (n * 2)
arrTempX = Rhino.XFormCPlaneToWorld( Array((2 * Rhino.Distance(arrCenter,arrXDir)),0,0), Array(arrCenter,XAxis,YAxis,ZAxis))
arrTempY = Rhino.XFormCPlaneToWorld( Array(0,(2 * Rhino.Distance(arrCenter,arrYDir)),0), Array(arrCenter,XAxis,YAxis,ZAxis))
arrTempZ = arrZDir
d = 5 ' subtract center from axes
StrX = Round(arrTempX(0)-arrCenter(0),d) & " " & Round(arrTempX(1)-arrCenter(1),d) & " " & Round(arrTempX(2)-arrCenter(2),d) & " 0"
StrY = Round(arrTempY(0)-arrCenter(0),d) & " " & Round(arrTempY(1)-arrCenter(1),d) & " " & Round(arrTempY(2)-arrCenter(2),d) & " 0"
StrZ = Round(arrTempZ(0)-arrCenter(0),d) & " " & Round(arrTempZ(1)-arrCenter(1),d) & " " & Round(arrTempZ(2)-arrCenter(2),d) & " 0"
StrC = Round(arrCenter(0),d) & " " & Round(arrCenter(1),d) & " " & Round(arrCenter(2),d) & " 1"
' return 4x4 matrix and strength ' (arrXAxis arrYAxis arrZAxis arrOrigin dblStrength)
GET_PlaneMatrix = StrX & vbTab & StrY & vbTab & StrZ & vbTab & StrC & vbTab & dblStrength
End Function

RiBlobbyExporter
