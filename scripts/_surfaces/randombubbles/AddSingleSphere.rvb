' Script for Rhinoceros 3.0 Sr3
' add single RiBlobby 1001 object (Sphere) to render with RiBlobby Exporter
' © 2004 Clement Greiner

Option Explicit
Sub AddSingleSphere
Dim blnCommand, IntRiInfluence, StrRiInfluence, StrSphere

' search for a default RiBlobby influence in this document, define
	intRiInfluence = Rhino.GetDocumentData("RandomBubbles", "RiInfluence")
	If IsNull(intRiInfluence) Then intRiInfluence = 1

' define influence
	If intRiInfluence = 1 Then StrRiInfluence = "Positive" Else StrRiInfluence = "Negative"
	StrRiInfluence = Rhino.GetString("Choose RiBlobby Influence mode", StrRiInfluence, Array("Positive","Negative"))
	If IsNull(StrRiInfluence) Then Exit Sub
	If StrRiInfluence = "Positive" Then IntRiInfluence = 1 Else IntRiInfluence = -1
	' store
	Rhino.SetDocumentData "RandomBubbles", "RiInfluence", intRiInfluence
Do
	blnCommand = Rhino.Command("_Sphere")
	If blnCommand = vbTrue Then
		StrSphere= Rhino.LastObject
		ADD_BubbleUserData StrSphere, intRiInfluence
	Else
		Exit Do
	End If
Loop

End Sub

' Function to add 1001 bubble user data to spheres
Private Function ADD_BubbleUserData (StrObject, intRiBlobbyInfluence)
Dim StrInfluence
If intRiBlobbyInfluence = -1 Then StrInfluence = "Negative" Else StrInfluence = "Positive"
' store the "Opcode" to include this object as 1001 (ellipsoid) = spherical
Rhino.SetObjectData StrObject, "RandomBubbles", "RiOpcode", 1001
' store the sphere center point and radius for collision detection
Rhino.SetObjectData  StrObject, "RandomBubbles", "RiInfluence", intRiBlobbyInfluence
' display the data values to assign
Rhino.Print "RiOpcode: " & 1001 &  "  RiInfluence: " & StrInfluence
End Function

AddSingleSphere
