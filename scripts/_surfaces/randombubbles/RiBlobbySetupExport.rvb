' script for Rhinoceros 3.0 Sr3
' generate a rib archive with RiBlobby information from spheres generated by RandomBubbles Script
' setup exporter script
' © 2004 Clement Greiner

Option Explicit
Sub SetupExport

Dim arrOptions(11), count, blnState, arrStates, blnResult, arrResults
Dim msg, Value, StrArchivePath
Dim intEnable

' define option strings
arrOptions(0) = " Print export progress to CommandLine"
arrOptions(1) = " Include RiBlobby annotations to RIB file"
arrOptions(2) = " Use RhinoMan`s default output directory"
arrOptions(3) = " Adjust Clipping before starting rendering"
arrOptions(4) = " Allocate Plane DBO inside output directory"
arrOptions(5) = " Assign vertex coloring to RiBlobby objects"
arrOptions(6) = " Invert negative Ellipsoid colors (1001)"
arrOptions(7) = " Invert negative Segment colors (1002)"
arrOptions(8) = " Invert negative Plane colors (9000)"
arrOptions(9) = " Positive Influence between negative blobs"
arrOptions(10)= " Include RIB: ShadingInterpolation " & CHR(34) & "smooth" & CHR(34)
arrOptions(11)= " AutoRender RiBlobby Scene after RIB export"

' define default booleans for each option if not made for this document
intEnable = Rhino.GetDocumentData("RiBlobbyExporter", "PrintProgress")
If IsNull(IntEnable) Then
	Print "Reading default exporter setup"
	arrStates = GET_DocumentDefaults
Else
	' read from document
	Print "Reading exporter setup data from document..."
	arrStates = READ_ExporterSetup
End If

' display all options
arrResults = Rhino.CheckListBox (arrOptions, arrStates, "Toggle RIB export options to include/exclude:", "RiBlobby setup export...")
If IsNull(arrResults) Then Print "Command canceled" : Exit Sub

' store option(0) - "Exclude Locked and Hidden RiBlobby objects"
If arrResults(0) = vbTrue Then Value = 1 Else Value = 0
Rhino.SetDocumentData "RiBlobbyExporter", "PrintProgress" , Value
' store option(1) - "include 1002"
If arrResults(1) = vbTrue Then Value = 1 Else Value = 0
Rhino.SetDocumentData "RiBlobbyExporter", "IncludeAnnotation" , Value

' store option(2) - define output path location
If arrResults(2) = vbTrue Then
	' define default path, read rhinoman output directory from registry, if not existing, choose path
	StrArchivePath = Rhino.GetDocumentData("RiBlobbyExporter", "ArchivePath")
	If IsNull(StrArchivePath) Then StrArchivePath = GET_RhinoManDefaultPath

	If StrArchivePath = "ERROR" Then StrArchivePath = GET_DefaultPath
	If StrArchivePath = "ERROR" Then Rhino.Print "Command aborted, no path specified." : Exit Sub
	' store the option and path
	Rhino.SetDocumentData "RiBlobbyExporter", "UseDefaultPath", 1
	Rhino.SetDocumentData "RiBlobbyExporter", "ArchivePath", StrArchivePath
End If

' define a different path, instead of rhinoman default dir
If arrResults(2) = vbFalse Then

	StrArchivePath = GET_DefaultPath
	If IsNull(StrArchivePath) Then Rhino.Print "Command aborted." : Exit Sub

	' use this path as new default path, re-enable this setting
	Rhino.SetDocumentData "RiBlobbyExporter", "UseDefaultPath", 1
	' store the path
	Rhino.SetDocumentData "RiBlobbyExporter", "ArchivePath", StrArchivePath
End If

' store option(3) - Update locations
If arrResults(3) = vbTrue Then Value = 1 Else Value = 0
Rhino.SetDocumentData "RiBlobbyExporter", "AdjustClipping", Value

'  store option(4)
If arrResults(4) = vbTrue Then Value = 1 Else Value = 0
Rhino.SetDocumentData "RiBlobbyExporter", "AllocatePlaneDBO", Value

' store option(5) - assign vertex colors derived from object wireframe color
If arrResults(5) = vbTrue Then Value = 1 Else Value = 0
Rhino.SetDocumentData "RiBlobbyExporter", "VertexColors", Value

' store option(6) - Invert colors for negative ellipsoids
If arrResults(6) = vbTrue Then Value = 1 Else Value = 0
Rhino.SetDocumentData "RiBlobbyExporter", "Invert1001", Value

' store option(7) - Invert colors for negative segments
If arrResults(7) = vbTrue Then Value = 1 Else Value = 0
Rhino.SetDocumentData "RiBlobbyExporter", "Invert1002", Value

' store option(8) - Invert colors for negative plane dbo
If arrResults(8) = vbTrue Then Value = 1 Else Value = 0
Rhino.SetDocumentData "RiBlobbyExporter", "Invert9000", Value

' store option(9)
If arrResults(9) = vbTrue Then Value = 1 Else Value = 0
Rhino.SetDocumentData "RiBlobbyExporter", "AddSubtractors", Value

' store Option(10)
If arrResults(10) = vbTrue Then Value = 1 Else Value = 0
Rhino.SetDocumentData "RiBlobbyExporter", "ShadingSmooth", Value

' store Option(11)
If arrResults(11) = vbTrue Then Value = 1 Else Value = 0
Rhino.SetDocumentData "RiBlobbyExporter", "Render", Value

LIST_DocumentData

print "ready"
End Sub

' function to set defaults for first run
Private Function GET_DocumentDefaults
Dim arrDefaultStates(11)
arrDefaultStates(0) = 1
arrDefaultStates(1) = 1
arrDefaultStates(2) = 1
arrDefaultStates(3) = 1
arrDefaultStates(4) = 0
arrDefaultStates(5) = 0
arrDefaultStates(6) = 1
arrDefaultStates(7) = 1
arrDefaultStates(8) = 1
arrDefaultStates(9) = 1
arrDefaultStates(10)= 0
arrDefaultStates(11)= 1
GET_DocumentDefaults = arrDefaultStates
End Function

' function to read assignments
Private Function READ_ExporterSetup
Dim arrSetupStates(11), blnStat, arrblnStates(), sCount
arrSetupStates(0) = Rhino.GetDocumentData("RiBlobbyExporter", "PrintProgress")
arrSetupStates(1) = Rhino.GetDocumentData("RiBlobbyExporter", "IncludeAnnotation")
arrSetupStates(2) = Rhino.GetDocumentData("RiBlobbyExporter", "UseDefaultPath")
arrSetupStates(3) = Rhino.GetDocumentData("RiBlobbyExporter", "AdjustClipping")
arrSetupStates(4) = Rhino.GetDocumentData("RiBlobbyExporter", "AllocatePlaneDBO")
arrSetupStates(5) = Rhino.GetDocumentData("RiBlobbyExporter", "VertexColors")
arrSetupStates(6) = Rhino.GetDocumentData("RiBlobbyExporter", "Invert1001")
arrSetupStates(7) = Rhino.GetDocumentData("RiBlobbyExporter", "Invert1002")
arrSetupStates(8) = Rhino.GetDocumentData("RiBlobbyExporter", "Invert9000")
arrSetupStates(9) = Rhino.GetDocumentData("RiBlobbyExporter", "AddSubtractors")
arrSetupStates(10)= Rhino.GetDocumentData("RiBlobbyExporter", "ShadingSmooth")
arrSetupStates(11)= Rhino.GetDocumentData("RiBlobbyExporter", "Render")
sCount = 0
For Each blnStat in arrSetupStates
	Redim Preserve arrblnStates(sCount)
	If arrSetupStates(sCount) = 1 Then arrblnStates(sCount) = vbTrue Else arrblnStates(sCount) = vbFalse
	sCount = sCount + 1
Next
READ_ExporterSetup = arrblnStates
End Function

' function to list made assignments (redundant)
Function LIST_DocumentData
Dim StrList
Print "---------------------------------------------"
' option 0,1
StrList = Rhino.GetDocumentData("RiBlobbyExporter", "PrintProgress")
Print "(0) PrintProgress = " & StrList
StrList = Rhino.GetDocumentData("RiBlobbyExporter", "IncludeAnnotation")
Print "(1) IncludeAnnotation = " & StrList
' option 2
StrList = Rhino.GetDocumentData("RiBlobbyExporter", "UseDefaultPath")
Print "(2) UseDefaultPath = " & StrList
StrList = Rhino.GetDocumentData("RiBlobbyExporter", "ArchivePath")
Print "(X) ArchivePath = " & StrList
' option 3 - clipping
StrList = Rhino.GetDocumentData("RiBlobbyExporter", "AdjustClipping")
Print "(3) AdjustClipping = " & StrList
' option 4 - plane dbo allocation at output path
StrList = Rhino.GetDocumentData("RiBlobbyExporter", "AllocatePlaneDBO")
Print "(4) AllocatePlaneDBO = " & StrList
' option 5,6,7,8 (coloring)
StrList = Rhino.GetDocumentData("RiBlobbyExporter", "VertexColors")
Print "(5) VertexColors = " & StrList
StrList = Rhino.GetDocumentData("RiBlobbyExporter", "Invert1001")
Print "(6) InvertNegativeEllipsoidColors = " & StrList
StrList = Rhino.GetDocumentData("RiBlobbyExporter", "Invert1002")
Print "(7) InvertNegativeSegmentColors = " & StrList
StrList = Rhino.GetDocumentData("RiBlobbyExporter", "Invert9000")
Print "(8) InvertNegativePlaneColors = " & StrList
' option 9 (group or add neg. objs)
StrList = Rhino.GetDocumentData("RiBlobbyExporter", "AddSubtractors")
Print "(9) AddSubtractors = " & StrList
' option 10 (rib option)
StrList = Rhino.GetDocumentData("RiBlobbyExporter", "ShadingSmooth")
Print "(10) ShadingSmooth = " & StrList
' option 11 (hide render show)
StrList = Rhino.GetDocumentData("RiBlobbyExporter", "Render")
Print "(11) Render = " & StrList
End Function

' function to read the rhinoman default path from registry
Private Function GET_RhinoManDefaultPath
Dim Sh, key, a
On Error Resume Next
Set Sh = CreateObject("WScript.Shell")
key = "HKEY_CURRENT_USER\Software\McNeel\Rhinoceros\3.0\Scheme: Default\Plug-ins\0AC6FEA5-68A5-4856-8677-6AF9C3E99C3A\Settings\OutputPath"
a = Sh.RegRead (key)
If Len(a) = 0 Then
	Rhino.Print "The registry key to read the RhinoMan default path cannot be found", vbOkOnly , "ReadDefaultPath"
	GET_RhinoManDefaultPath = "ERROR"
Else
	Rhino.Print "Reading RhinoMan default directory from registry : " & CHR(34) & a & CHR(34)
	GET_RhinoManDefaultPath = a
End If
Set Sh = Nothing
End Function

' function to manually select archibe.rib output path
Private Function GET_DefaultPath
Dim StrPath
StrPath = Rhino.BrowseForFolder( , "Select a destination folder to create RiBlobby file " & CHR(34) & "archive.rib" & CHR(34) , "OutputFolder" )
If IsNull(StrPath) Then
	GET_DefaultPath = "C:\"
Else
	Rhino.Print "Default RiBlobby output folder has been set to : " & CHR(34) & StrPath & CHR(34)
	GET_DefaultPath = StrPath
End If
End Function


SetupExport
