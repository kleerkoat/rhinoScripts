' Script for Rhinoceros 3.0 Sr3
' Select RiBlobby Objects by type (1001,1002,9000) => (ellipsoids, segments, planes)
' © 2004 Clement Greiner
Option Explicit
Sub SelectBlobbyObjectsByInfluence
Dim arrAllowed, StrObj, StrObjInfluence, arrSelection(), count
arrAllowed = GET_RiObjects
If Not IsArray(arrAllowed) Then Print "No selectable RiObjects found in document." : Exit Sub
StrObjInfluence = Rhino.GetString("Choose object type to select", "Positive", Array("Positive","Negative"))
If IsNull(StrObjInfluence) Then Print "Command aborted" : Exit Sub
' select by influence
count = 0
For Each StrObj In arrAllowed
	' include ellipsoids
	If StrObjInfluence = "Positive" Then
		If Int(Rhino.GetObjectData(StrObj, "RandomBubbles", "RiInfluence")) = 1 Then
			ReDim Preserve arrSelection(count)
			arrSelection(count) = StrObj
			count = count + 1
		End If
	ElseIf StrObjInfluence = "Negative" Then
		If Int(Rhino.GetObjectData(StrObj, "RandomBubbles", "RiInfluence")) = -1 Then
			ReDim Preserve arrSelection(count)
			arrSelection(count) = StrObj
			count = count + 1
		End If
	End If
Next

If count = 0 Then Print "No " & LCase(StrObjInfluence) & " Ri_Objects found ": Exit Sub
Rhino.SelectObjects arrSelection
Rhino.Print "Selected " & count & " " & LCase(StrObjInfluence) & " Ri_Blobby objects."
End Sub

Private Function GET_RiObjects
Dim arrAllObjs, count, StrObject, StrValue, arrRiObjs()
arrAllObjs = Rhino.NormalObjects
' exit if document is empty
If Not IsArray(arrAllObjs) Then GET_RiObjects = vbNull : Exit Function
' search objects for planes
count = 0
For Each StrObject In arrAllObjs
	StrValue = Int(Rhino.GetObjectData(StrObject, "RandomBubbles","RiOpcode"))
	If StrValue = 9000 Or StrValue = 1001 Or StrValue = 1002 Then
		ReDim Preserve arrRiObjs(count)
		arrRiObjs(count) = StrObject
		count = count + 1
	End If
Next
If count > 0 Then GET_RiObjects = arrRiObjs Else GET_RiObjects = vbNull
End Function

SelectBlobbyObjectsByInfluence
