' ****************************** RhinoScript.org ******************************
'
'   n-closest point, version 1
'
'   by Johannes Kuhnen, published Jun 08, 2010
'
'
'   Finds the point in an array of 3-D points that is the 1st, 2nd, 3rd, .... n-closest point to a test point.
'   It is a similar function like Rhino.PointArrayClosestPoint() but with a range.
'   The return is the index of that point.
'
'
'
'
'   This RhinoScript Library has been downloaded from RhinoScript.org.
'
'   Rhino versions: Rhino 4 (at least service release 7)
'   In order to run it you need the following libraries: "Array Library" (version 1.4) by Hanno Stehling.
'
'   LICENSE INFORMATION:
'   This script is published under the GNU General Public License, version 3
'   or any later version, and thus comes WITHOUT ANY WARRANTY. You can get
'   the complete license text here: www.rhinoscript.org/gpl
'
' ****************************** RhinoScript.org ******************************



Option Explicit

' +++ NClosestPoint +++
' Finds the point in an array of 3d points that is n-closest to a test point.

' [Parameters]
' arrPoints	: 	Array, 3d points
' arrPoint	:	Array, 3d point	, test point 
' range		: 	Integer, 0 = closest, 1 = 2nd closest, 2 = 3rd closest,...

' [Returns]
' Number 	: Integer, the index of the n-closest point
' Null  	: on error

Function NClosestPoint(arrPoints, arrPoint, range)

	NClosestPoint = Null
	
	If range > Ubound(arrPoints) Then
		Exit Function
	End If
	
	Dim arrTemp	: arrTemp = arrPoints
	Dim i
	
	If range > 0 Then
		For i = 0 To range - 1
			Call array_extract(arrTemp, Rhino.PointArrayClosestPoint(arrTemp, arrPoint))
		Next
	End If
	
	NClosestPoint = Rhino.PointArrayClosestPoint(arrTemp, arrPoint)

End Function
