Option Explicit

'Script written by Pascal

'Script version Friday, July 11, 2008

Sub OffsetCrvLoose()
	
	Dim all: aLl = Rhino.NormalObjects
	Dim sAll, i, aOn()
	i = 0
	
	Dim temp: temp = Rhino.GetObject("Select curve to offset", 4,True)
	If isNull(temp) Then Exit Sub

	For Each sAll In All
		
		If Rhino.ObjectGripsOn(sAll) Then
			ReDim Preserve aOn(i)
			aOn(i) = sAll
			i = i + 1
			Rhino.EnableObjectGrips sAll,False
		End If
		
	Next
	
	Dim aLock: aLock = Rhino.ObjectsByType(1)
	
	If isArray(aLock) Then
		Rhino.LockObjects(aLock)
	End If
	
	Dim sCrv: sCrv = Rhino.CopyObject(temp)
	Rhino.SelectObject sCrv
	
	Rhino.Command "_Offset "
	
	If Rhino.LastCommandResult = 0 Then
		Dim aResult: aResult = Rhino.LastCreatedObjects
		Dim starg: sTarg = aresult(0)
	End If
	
	Rhino.EnableRedraw(False)
	
	Rhino.Command "_EditPtOn ", False
		
	Rhino.Command "_SelPt ", False
	
	Dim aGrips:aGrips = Rhino.SelectedObjectGrips(sCrv)
	
	If Not isArray(aGrips) Then
		
		Cleanup aLock, aOn, sCrv
		Exit Sub
		
	End If

	Dim Grip, aPt, aTarg(), n
	n = 0

	Dim temp2
	For Each Grip In aGrips
		
		Apt = Rhino.ObjectGripLocation(sCrv,Grip)
	
		temp = Rhino.CurveClosestPoint(sTarg,apt)
		temp2 = Rhino.EvaluateCurve(starg,temp)
		If Not isNull(temp) Then
			ReDim Preserve atarg(n)
			aTarg(n) = temp2

			n = n +1
		End If
			
	Next
	Rhino.DeleteObject starg
	
	If n-1 = uBound(aGrips) Then
		
	For i= 0 To UBound(aGrips)
		Rhino.ObjectGripLocation sCrv, agrips(i), aTarg(i)
	Next
	 
	Else 
	MsgBox "Projection misses or partly misses the target."
	cleanup aLock, aOn, sCrv
	Exit Sub
	End If
	
	Rhino.Command "_PointsOff "	, False
	
	rhino.EnableRedraw
	
End Sub

'Rhino.AddStartUpScript Rhino.LastLoadedScriptFile
'Rhino.AddAlias "OffSetLoose", "_NoEcho _-RunScript (OffSetLoose)"

Function IsUpperBound(ByRef arr)

	IsUpperBound = False

	If IsArray(arr) Then

		On Error Resume Next

		UBound arr

		If Err.Number = 0 Then IsUpperBound = True

	End If

End Function


Sub Cleanup(aLock, aOn, sCrv)
		
	Rhino.Command "_PointsOff "	, False
	
	If isArray(aLock) Then
		Rhino.UnlockObjects aLock
	End If
	
	Dim sOn
	
	If isUpperBound(aOn) Then
		For Each sOn In aOn
			Rhino.EnableObjectgrips sOn,True
		Next
	End If
	
	Rhino.DeleteObject sCrv
	Rhino.EnableRedraw
	
End Sub
