'--------------------------------------------------------------
'Command   :  cv4 (curve 4 points count)
'Date      :  2011/02/01
'Version   :  1.0
'Organization   :  Rhino+
'--------------------------------------------------------------
Sub crvRebuild4pts

Dim strCurve ,strCurves

strCurves = Rhino.GetObjects("Select change curve 4 pionts count",4,True,True)

If IsNull(strCurves) Then Exit Sub

For Each strCurve In strCurves
  
  If Not IsNull(strCurve) Then

    Rhino.RebuildCurve strCurve, 3, 4

  End If

Next

End Sub

'CrvRebuild4pts
