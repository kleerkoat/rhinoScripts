Option Explicit

'Script written by Pascal
'Script version Thursday, July 02, 2009 
'removes arcs from polycurves and extends the neighboring segments if possible
'to sharpen the corners.
	

'Rhino.AddStartupScript Rhino.LastLoadedScriptFile
'Rhino.AddAlias "SharpenAll", "_NoEcho _-Runscript (SharpenAll)"

'Call SharpenAll()

Sub SharpenAll()
	
	Dim aObj:  aObj = Rhino.GetObjects("Select polycurves",4,,True)
	If Not isArray(aObj) Then Exit Sub
	
	Dim Curves, aCrvs, sCrv, i,aPt, tempCrv, sObj
	Dim PrevCrv, nxtCrv, newSegs, aJoin, aStart, stemp
	Dim K, j, G
	
	Rhino.EnableRedraw(False)
	
	For Each sObj In aObj

	
	
		If  Rhino.IsPolyCurve(sObj) Or Rhino.IsPolyline(sObj) Then
	
			sTemp = Rhino.CopyObject (sobj)
	
			aStart = Rhino.CurveStartPoint(sObj)
			Rhino.LockObject sObj
	
	
			Do
				G = False	
				aCrvs = Rhino.ExplodeCurves( sTemp,True)
	
				If Not isArray(aCrvs) Then Exit Sub
	
				Set Curves = CreateObject("Scripting.Dictionary")
	
				For i = 0 To ubound(aCrvs)
		
					Curves.Add i,acrvs(i)
		
				Next
	
				NewSegs = False
				For j = 0 To ubound(aCrvs)
		
					K = False' this is a check on whther the segment is a start or end segment
					'this is reset for every For-Loop in the Do-Loop
		
					If Rhino.IsArc(aCrvs(j)) Then
						tempCrv = aCrvs(j)
				
						'if the arc is an end segment, then G stays false- 
						'this determines whether To Loop again Or Not
						'in the overall Do-Loop
						If j>0 And j<Ubound(aCrvs) Then
							G = True
						End If
		
				
						If Rhino.PointCompare(aStart, Rhino.CurveStartPoint(tempCrv),0.0001) Then
							K = True
							PrevCrv = Curves.Item(Ubound(aCrvs))
							NxtCrv = Curves.Item(1)
				
							Rhino.EnableRedraw(False)
							NewSegs = ExtendToIntersection(PrevCrv,NxtCrv)
			
							If isArray(newSegs) Then
				
								Curves.Remove Ubound(aCrvs)
								Curves.Remove 1
								Curves.Add Ubound(aCrvs),newSegs(0)
								Curves.Add 1,newSegs(1)
								Rhino.DeleteObject tempCrv
								NewSegs = True
							End If
			
						ElseIf	Rhino.PointCompare(aStart, Rhino.CurveEndPoint(tempCrv),0.0001) Then
			
							K = True
							PrevCrv = Curves.Item(Ubound(aCrvs)-1)
							NxtCrv = Curves.Item(0)
			
							NewSegs = ExtendToIntersection(PrevCrv,NxtCrv)
			
							If isArray(newSegs) Then
				
								Curves.Remove Ubound(aCrvs)-1
								Curves.Remove 0
								Curves.Add Ubound(aCrvs)-1,newSegs(0)
								Curves.Add 0,newSegs(1)
								Rhino.DeleteObject tempCrv
								NewSegs = True
							End If

						End If
		
						If K = False Then
							For i = 0 To uBound(aCrvs)
								If Curves.item(i) = tempCrv Then Exit For
							Next
		
							If Not isNull(tempCrv) Then
			
								PrevCrv = Curves.Item(i-1)
								NxtCrv = Curves.Item(i+1)
								NewSegs = ExtendToIntersection(PrevCrv,NxtCrv)
			
								If isArray(newSegs) Then
				
									Curves.Remove i-1
									Curves.Remove i+1
									Curves.Add i-1,newSegs(0)
									Curves.Add i+1,newSegs(1)
									Rhino.DeleteObject tempCrv
									NewSegs = True
								End If
			
							End If
						End If
					End If
		
				Next
		
				ReDim aJoin(Ubound(aCrvs))
		
				For i = 0 To ubound(aCrvs)
					aJoin(i) = Curves.Item(i)
				Next
				stemp = Rhino.JoinCurves (aJoin,True)
		
		
			Loop Until G = False Or NewSegs = False
		
			Rhino.EnableRedraw(False)
	
			Rhino.UnlockObject sObj
			Rhino.DeleteObject sobj
			
		End If
	Next
	
	Rhino.EnableRedraw(True)
	
End Sub


Function ExtendToIntersection(PrevCrv,NxtCrv)
	
	'Rhino.EnableRedraw(False)
	
	Dim input1, Input2
	Input1 = Rhino.CopyObject(PrevCrv)
	Input2 =  Rhino.CopyObject(NxtCrv)
	
	Dim Vectan
	
	Dim base1:Base1 = Rhino.CurveEndPoint(Input1)
	Dim base2: Base2 = Rhino.CurveStartPoint(Input2)
	
	Vectan = Rhino.CurveTangent(Input1,Rhino.CurveDomain(Input1)(1))
	Dim Line1: Line1 = array(Base1,Rhino.PointAdd(Base1,VecTan))

	Vectan = Rhino.CurveTangent(Input2,Rhino.CurveDomain(Input2)(0))
	Dim Line2: Line2 = array(Base2,,Rhino.PointAdd(Base2,VecTan))
	
	Dim tempPt: tempPt = Rhino.LineLineIntersection(Line1, Line2)
	If Not isArray(TempPt) Then 
		Rhino.DeleteObjects array(Input1, input2)
		'Rhino.EnableRedraw(True)
		Exit Function
	End If

	Dim Crv1: Crv1 = Rhino.ExtendCurveLength(Input1,0,1,Rhino.Distance(Rhino.CurveEndPoint(Input1),tempPt))
	
	If isNull(Crv1) Then 
		Rhino.DeleteObjects array(Input1, Input2)
		'Rhino.Enableredraw(True)
		Exit Function
	End If
	
	Dim Crv2: Crv2 = Rhino.ExtendCurveLength(Input2,0,0,Rhino.Distance(Rhino.CurveStartPoint(Input2),tempPt))
	
	If isNull(Crv2) Then 
		Rhino.DeleteObjects array(Crv1, Input2)
		'Rhino.Enableredraw(True)
		Exit Function
	End If
	
	Dim X : X = Rhino.CurveCurveIntersection(Crv1,Crv2)
	
	If Not IsArray(X) Then 
		Rhino.DeleteObjects array(Crv1,Crv2,Input1,Input2)
		'Rhino.EnableRedraw(True)
		Exit Function
	End If
	
	If  X(0,0) = 2 Then 
		
		Rhino.DeleteObjects array(Crv1,Crv2,Input1,Input2)
		'Rhino.EnableRedraw(True)
		Exit Function
	End If
	
	Dim testpar1: testpar1 = Rhino.CurveClosestPoint(PrevCrv,X(0,1))
	Dim testpar2: testpar2 = Rhino.CurveClosestPoint(NxtCrv,X(0,1))
	
	Dim aSplit
	If testPar1 < Rhino.CurveDomain(PrevCrv)(1) Then
		'MsgBox "OK1"
		aSplit = Rhino.SplitCurve(Crv1,X(0,5))

	
		If isArray(aSplit) Then
			If uBound(aSplit) = 1 Then
				Rhino.DeleteObject Crv1
				If Rhino.CurveDomain(aSplit(1))(1) > Rhino.CurveDomain(aSplit(0))(1) Then
					Rhino.DeleteObject aSplit(1)
					Crv1 = ASplit(0)
				Else
					Rhino.DeleteObject aSplit(0)
					Crv1 = ASplit(1)
				End If
			Else Rhino.Deleteobjects aSplit
			End If
		End If
	End If
	
	
	If testPar2<Rhino.CurveDomain(NxtCrv)(1) Then
		'MsgBox "OK2"
		aSplit = Rhino.SplitCurve(Crv2,X(0,7),False)

		If isArray(aSplit) Then
			If uBound(aSplit) = 1 Then
				Rhino.DeleteObject Crv2
				If Rhino.CurveDomain(aSplit(1))(1) < Rhino.CurveDomain(aSplit(0))(1) Then
					Rhino.DeleteObject aSplit(1)
					
					Crv2 = ASplit(0)
				Else
					Rhino.DeleteObject aSplit(0)
					Crv2 = ASplit(1)
				End If
				
			Else Rhino.Deleteobjects aSplit
			End If
		End If
	End If
	Rhino.DeleteObjects array(PrevCrv,NxtCrv)
	ExtendToIntersection = array(Crv1,Crv2)
	
	' Rhino.EnableRedraw(True)
	
End Function
