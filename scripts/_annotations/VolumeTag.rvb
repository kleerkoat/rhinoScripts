Option explicit
'adds a Dot at the selected objects' centroid
'with the object volume in current file units

Rhino.AddStartupScript Rhino.LastLoadedScriptFile
Rhino.AddAlias "VolumeTag","_NoEcho _-Runscript (VolumeTag)"

Sub VolumeTag
  
	Dim arrObj, strObj,  strVol, arrVolume, strVolume, arrCent, arr3dCent, arrThings, strDot, strGroup
  
	arrObj = Rhino.GetObjects("Select closed objects for volume tag", 8+16+32,,True)
  
	If IsArray(arrObj) Then
		
		For Each strObj In arrobj
			
			arrvolume = Null
			arrCent = Null
			arr3dCent = Null
      
      
			If Rhino.IsSurface(strObj) Or Rhino.isPolysurface(strObj) Then
				
				If Rhino.isObjectSolid(strObj) Then
					arrVolume = Rhino.SurfaceVolume(strObj)
					strVolume = Round(arrVolume(0), 4)
					arrCent = Rhino.SurfaceVolumeCentroid(strObj)
					arr3dCent = arrCent(0) 
				End If

			ElseIf  Rhino.IsMesh(strObj) Then
				
				If Rhino.IsMeshClosed(strObj) Then
					arrVolume = Rhino.MeshVolume(strObj)
					strVolume = Round(arrVolume(1), 4)
					arr3dCent = Rhino.MeshAreaCentroid(strObj)
				End If
				
			End If
      
			If IsArray(arr3dCent) Then
				strDot = Rhino.AddTextDot ("Vol = " & strVolume, arr3dCent)
				strgroup = Rhino.addGroup
				arrThings = array(strDot, strObj)
				Rhino.AddObjectsToGroup arrThings, strGroup
			End If
      
		Next
		
	End If 
    
End Sub
