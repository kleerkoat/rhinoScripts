Option Explicit


Sub GroupNamer

	Dim arrobjects, strGroup,  arrCulled
	Dim arrValues(),  arrGroups(), arrSelGroups()
	Dim arrRename, arrGroup1
	Dim i,p,q,r,t,x
  
	i=0
	p=0
	q=0
	r=0
	t=0
	x=0 
  
	arrObjects = Rhino.GetObjects( "Select groups to rename" ,, True, True)
  
	If IsArray(arrObjects) Then
		For i =0 To UBound (arrObjects)
			arrGroup1 = (Rhino.ObjectGroups (arrObjects(i)))
			' Build a  list of the groups for the selected objects   
			If IsArray(arrGroup1) Then
				x=1  'switch tells the script at least one group exits in the selection
				For r = 0 To UBound(arrGroup1)
					ReDim Preserve arrSelGroups(p)
					arrSelGroups(p) = arrGroup1(r)
					p = p+1
					r = r+1
				Next
				Erase arrGroup1
				r=0
				i = i+1 
			End If
		Next
	Else Exit Sub
	End If
    
	'Cull any duplicate group names from the list 
 
	If IsUpperBound(arrSelGroups) And X=1 Then
		arrCulled = Rhino.CullDuplicateStrings(arrSelGroups)
	Else 
		Rhino.Print "None of the selected objects belongs to a group"
		Exit Sub
	End If
        
	' Get the changed group names from the user
	arrRename = Rhino.PropertyListBox (arrCulled, arrCulled, "Change group names", "Group Namer")
   
	'Rename the groups
	If IsArray(arrRename) Then
		t =0
		For t=0 To UBound(arrCulled)
			Rhino.RenameGroup arrCulled(t), arrRename(t)
		Next
	Else 
		Exit Sub
	End If
        
	Erase arrCulled
	Erase arrSelGroups

End Sub

Rhino.AddAlias "GroupNamer" , "! _-Runscript GroupNamer"
Rhino.AddStartupScript Rhino.LastLoadedScriptFile

Function IsUpperBound(ByRef arr)

	IsUpperBound = False

	If IsArray(arr) Then

		On Error Resume Next

		UBound arr

		If Err.Number = 0 Then IsUpperBound = True

	End If

End Function
