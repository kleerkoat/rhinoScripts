Option Explicit

Call DeltoidalHexecontahedron

Sub DeltoidalHexecontahedron

  Dim C0, C1, C2, C3, C4, C5, C6, C7, C8  
  Dim V(), F()
  
  C0 = (5 - Sqr(5)) / 4
  C1 = (15 + Sqr(5)) / 22
  C2 = Sqr(5) / 2
  C3 = (5 + Sqr(5)) / 6
  C4 = (5 + 4 * Sqr(5)) / 11
  C5 = (5 + Sqr(5)) / 4
  C6 = (5 + 3 * Sqr(5)) / 6
  C7 = (25 + 9 * Sqr(5)) / 22
  C8 = Sqr(5)

  ReDim V(61)
  V(0)  = Array(0.0, 0.0,  C8)
  V(1)  = Array(0.0, 0.0, -C8)
  V(2)  = Array( C8, 0.0, 0.0)
  V(3)  = Array(-C8, 0.0, 0.0)
  V(4)  = Array(0.0,  C8, 0.0)
  V(5)  = Array(0.0, -C8, 0.0)
  V(6)  = Array( C0,  C2,  C5)
  V(7)  = Array( C0,  C2, -C5)
  V(8)  = Array( C0, -C2,  C5)
  V(9)  = Array( C0, -C2, -C5)
  V(10) = Array(-C0,  C2,  C5)
  V(11) = Array(-C0,  C2, -C5)
  V(12) = Array(-C0, -C2,  C5)
  V(13) = Array(-C0, -C2, -C5)
  V(14) = Array( C5,  C0,  C2)
  V(15) = Array( C5,  C0, -C2)
  V(16) = Array( C5, -C0,  C2)
  V(17) = Array( C5, -C0, -C2)
  V(18) = Array(-C5,  C0,  C2)
  V(19) = Array(-C5,  C0, -C2)
  V(20) = Array(-C5, -C0,  C2)
  V(21) = Array(-C5, -C0, -C2)
  V(22) = Array( C2,  C5,  C0)
  V(23) = Array( C2,  C5, -C0)
  V(24) = Array( C2, -C5,  C0)
  V(25) = Array( C2, -C5, -C0)
  V(26) = Array(-C2,  C5,  C0)
  V(27) = Array(-C2,  C5, -C0)
  V(28) = Array(-C2, -C5,  C0)
  V(29) = Array(-C2, -C5, -C0)
  V(30) = Array( C3, 0.0,  C6)
  V(31) = Array( C3, 0.0, -C6)
  V(32) = Array(-C3, 0.0,  C6)
  V(33) = Array(-C3, 0.0, -C6)
  V(34) = Array( C6,  C3, 0.0)
  V(35) = Array( C6, -C3, 0.0)
  V(36) = Array(-C6,  C3, 0.0)
  V(37) = Array(-C6, -C3, 0.0)
  V(38) = Array(0.0,  C6,  C3)
  V(39) = Array(0.0,  C6, -C3)
  V(40) = Array(0.0, -C6,  C3)
  V(41) = Array(0.0, -C6, -C3)
  V(42) = Array(0.0,  C1,  C7)
  V(43) = Array(0.0,  C1, -C7)
  V(44) = Array(0.0, -C1,  C7)
  V(45) = Array(0.0, -C1, -C7)
  V(46) = Array( C7, 0.0,  C1)
  V(47) = Array( C7, 0.0, -C1)
  V(48) = Array(-C7, 0.0,  C1)
  V(49) = Array(-C7, 0.0, -C1)
  V(50) = Array( C1,  C7, 0.0)
  V(51) = Array( C1, -C7, 0.0)
  V(52) = Array(-C1,  C7, 0.0)
  V(53) = Array(-C1, -C7, 0.0)
  V(54) = Array( C4,  C4,  C4)
  V(55) = Array( C4,  C4, -C4)
  V(56) = Array( C4, -C4,  C4)
  V(57) = Array( C4, -C4, -C4)
  V(58) = Array(-C4,  C4,  C4)
  V(59) = Array(-C4,  C4, -C4)
  V(60) = Array(-C4, -C4,  C4)
  V(61) = Array(-C4, -C4, -C4)

  ReDim F(59)
  F(0)  = Array( 30,  0, 44,  8 )
  F(1)  = Array( 30,  8, 56, 16 )
  F(2)  = Array( 30, 16, 46, 14 )
  F(3)  = Array( 30, 14, 54,  6 )
  F(4)  = Array( 30,  6, 42,  0 )
  F(5)  = Array( 31,  1, 43,  7 )
  F(6)  = Array( 31,  7, 55, 15 )
  F(7)  = Array( 31, 15, 47, 17 )
  F(8)  = Array( 31, 17, 57,  9 )
  F(9)  = Array( 31,  9, 45,  1 )
  F(10) = Array( 32,  0, 42, 10 )
  F(11) = Array( 32, 10, 58, 18 )
  F(12) = Array( 32, 18, 48, 20 )
  F(13) = Array( 32, 20, 60, 12 )
  F(14) = Array( 32, 12, 44,  0 )
  F(15) = Array( 33,  1, 45, 13 )
  F(16) = Array( 33, 13, 61, 21 )
  F(17) = Array( 33, 21, 49, 19 )
  F(18) = Array( 33, 19, 59, 11 )
  F(19) = Array( 33, 11, 43,  1 )
  F(20) = Array( 34,  2, 47, 15 )
  F(21) = Array( 34, 15, 55, 23 )
  F(22) = Array( 34, 23, 50, 22 )
  F(23) = Array( 34, 22, 54, 14 )
  F(24) = Array( 34, 14, 46,  2 )
  F(25) = Array( 35,  2, 46, 16 )
  F(26) = Array( 35, 16, 56, 24 )
  F(27) = Array( 35, 24, 51, 25 )
  F(28) = Array( 35, 25, 57, 17 )
  F(29) = Array( 35, 17, 47,  2 )
  F(30) = Array( 36,  3, 48, 18 )
  F(31) = Array( 36, 18, 58, 26 )
  F(32) = Array( 36, 26, 52, 27 )
  F(33) = Array( 36, 27, 59, 19 )
  F(34) = Array( 36, 19, 49,  3 )
  F(35) = Array( 37,  3, 49, 21 )
  F(36) = Array( 37, 21, 61, 29 )
  F(37) = Array( 37, 29, 53, 28 )
  F(38) = Array( 37, 28, 60, 20 )
  F(39) = Array( 37, 20, 48,  3 )
  F(40) = Array( 38,  4, 52, 26 )
  F(41) = Array( 38, 26, 58, 10 )
  F(42) = Array( 38, 10, 42,  6 )
  F(43) = Array( 38,  6, 54, 22 )
  F(44) = Array( 38, 22, 50,  4 )
  F(45) = Array( 39,  4, 50, 23 )
  F(46) = Array( 39, 23, 55,  7 )
  F(47) = Array( 39,  7, 43, 11 )
  F(48) = Array( 39, 11, 59, 27 )
  F(49) = Array( 39, 27, 52,  4 )
  F(50) = Array( 40,  5, 51, 24 )
  F(51) = Array( 40, 24, 56,  8 )
  F(52) = Array( 40,  8, 44, 12 )
  F(53) = Array( 40, 12, 60, 28 )
  F(54) = Array( 40, 28, 53,  5 )
  F(55) = Array( 41,  5, 53, 29 )
  F(56) = Array( 41, 29, 61, 13 )
  F(57) = Array( 41, 13, 45,  9 )
  F(58) = Array( 41,  9, 57, 25 )
  F(59) = Array( 41, 25, 51,  5 )

  Call CreatePolyhedra(V, F)

End Sub

Sub CreatePolyhedra(V, F)
	
	Dim face, pts(), pline, psrfs, srfs()
	Dim i, j
	
	Call Rhino.EnableRedraw(False)

	ReDim srfs(UBound(F))
	For i = 0 To UBound(F)
		face = F(i)
		ReDim pts(UBound(face)+1)
		For j = 0 To UBound(face)
			pts(j) = V(face(j))
		Next
		pts(UBound(face)+1) = pts(0)
		pline = Rhino.AddPolyline(pts)
		psrfs = Rhino.AddPlanarSrf(Array(pline))
		srfs(i) = psrfs(0)
		Call Rhino.DeleteObject(pline)
	Next

	Call Rhino.SelectObjects(srfs)
	Call Rhino.Command("_-Join", 0)
	Call Rhino.UnselectAllObjects

	Call Rhino.EnableRedraw(True)
	
End Sub
