' ****************************** RhinoScript.org ******************************
'
'   3point slice, version 1
'
'   by Johannes Kuhnen, published Oct 11, 2011
'
'
'   Slices a solid with 3point input.
'   This is an update of the "Slice" script build by rocha16041982.
'   
'   Changed parts of the syntax.
'
'
'
'
'   This RhinoScript Application has been downloaded from RhinoScript.org.
'   It is based on "slice" by RAMIRO ROCHA.
'
'   Rhino versions: Rhino 4 (at least service release 4)
'
'   LICENSE INFORMATION:
'   This script is published under the GNU General Public License, version 3
'   or any later version, and thus comes WITHOUT ANY WARRANTY. You can get
'   the complete license text here: www.rhinoscript.org/gpl
'
' ****************************** RhinoScript.org ******************************



'Call sliceSolid()

Sub 3PointSlice()

	Dim  Object1,Object2,arrPoints

	Object1 = Rhino.GetObjects("Select object to slice", 8 + 16)

	If IsArray(Object1) Then

		Object2 = Rhino.CopyObjects(Object1)

		If IsArray(Object2) Then

			Rhino.SelectObjects Object2

			arrPoints = Rhino.GetPoints (True, False , "Pick 3 Points",, 3 )


			Rhino.EnableRedraw False

			arrVector1= Rhino.VectorCreate (arrPoints(0), arrPoints(1) )
			arrVector2= Rhino.VectorCreate (arrPoints(0), arrPoints(2) )
			strCut = Rhino.AddCutPlane (object1, arrPoints(0), arrPoints(1) , arrVector2)
			arrBD = Rhino.BooleanDifference (object1, Array(strCut) )

			If IsArray(arrBD) Then 
				Rhino.ShrinkTrimmedSurface arrBD(0) 
				Rhino.SelectObjects arrBD
			Else
				Rhino.DeleteObject strCut
				Rhino.Print "Failed to Cut"
			End If

			Rhino.EnableRedraw True


		End If

	End If

	Rhino.EnableRedraw False

	arrVector1= Rhino.VectorCreate (arrPoints(1), arrPoints(0) )
	arrVector2= Rhino.VectorCreate (arrPoints(2), arrPoints(0) )
	strCut = Rhino.AddCutPlane (object2, arrPoints(0), arrPoints(1) , arrVector2)
	arrBD = Rhino.BooleanDifference (object2, Array(strCut) )

	If IsArray(arrBD) Then 
		Rhino.ShrinkTrimmedSurface arrBD(0) 
		Rhino.SelectObjects arrBD
	Else
		Rhino.DeleteObject strCut
		Rhino.Print "Failed to Cut"
	End If

	Rhino.EnableRedraw True

End Sub
