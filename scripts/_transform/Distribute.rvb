Option Explicit
'Script written by Pascal

'Script version Saturday, September 03, 2011 

'Rhino.AddStartupScript Rhino.LastLoadedScriptFile()
'Rhino.AddAlias "Distribute", "_NoEcho _-Runscript (Distribute)"
Private OldDDir, OldGapStyle

If IsEmpty(OldDDir) Then
	OldDDir = "X"
End If

If IsEmpty (OldGapStyle) Then
	OldGapStyle = "Centers"
End If

'Call Distribute()

Sub Distribute()
	Dim i
	Dim aObj: aObj = Rhino.GetObjects("Select objects to distribute.",,,True)
	If Not IsArray(aObj) Then Exit Sub
	
	Dim Bound: Bound = UBound(aObj)
	
	'get thew users choice of the distribution direction
	Dim aDir: aDir = Array("X","Y", "User")
	Dim sDir: sDir = Rhino.GetString("Direction", OldDDir,aDir)
	If IsNull(sDir) Then Exit Sub
	
	'check that the result is valid
	Dim intDir: intDir = WhereInArray(sDir,aDir, 1)
	
	If intDir = -1 Then Exit Sub
	
	'set the sticky option
	If intDir <> 2 Then
		OldDDir = UCase(sDir)
	Else
		oldDDir = "User"
	End If
	
	
	Dim TempPlane: TempPlane = Rhino.ViewCPlane()
	Dim Plane
	
	'Get a plane from the direction and the current cplane
	
	'if the direction is the cplane X, use the view cplane
	If intDir = 0 Then
		Plane = TempPlane
		
		'if the direction is Y rotate the plane on Z, 90 degrees
	ElseIf intDir = 1 Then 
		Plane = Rhino.RotatePlane(TempPlane,90,TempPlane(3))
	Else
		
		'get a plane from the user defined direction
		Plane = GetPlaneFromDirection()
		If Not IsArray(Plane) Then Exit Sub
	End If
	
	
	'get the gap style from the user- 
	'either between centers or by equal
	'spacing between bounding box edges
	Dim aStyle: aStyle = Array("Centers", "Gap")
	
	Dim sStyle: sStyle = Rhino.GetString("Set spacing style.", OldGapStyle, aStyle)
	If IsNull(aStyle) Then Exit Sub
	
	
	Dim intStyle: intStyle = WhereInArray(sStyle,aStyle, 1)
	
	If intStyle = -1 Then Exit Sub
	Dim blnStyle
	If intStyle = 0 Then
		OldGapStyle = "Centers"
		blnStyle = True
	Else
		oldGapStyle = "Gap"
		blnStyle = False
	End If



	'Order the selected objects in the direction to distribute
	' as well as an ordered set of BBox centers
	Dim Orderly: Orderly = OrderObjects(aObj, Plane)
	Dim aOrderedObj:aOrderedObj = Orderly(0)
	Dim aCen: aCen = Orderly(1)
'	
'	For I = 0 To Bound
'		Rhino.AddTextDot I, ACen(I)
'	Next


	Dim Space, span
	If BlnStyle = True Then 'Centers
	 
		'calculate the spacing between BB centers  fomr
		'the ordered array of Bbox centers.
		Space =  qDistance(aCen(0), aCen (Bound))/Bound
		
	Else 'gap
		'Calculate the desired space between bounding box edges
		Dim temp
		Dim ttl_length: ttl_length = 0
		
		'add up the total length of the middle objects in the distribute direction
		For i = 1 To Bound-1
			temp = Rhino.BoundingBox(aOrderedObj(i),Plane)
			ttl_length = ttl_length + qDistance(temp(0), temp(1))
		Next
		
		'find the max extent of the first object and the min extent of the last object
		'project the points to the plane X axis
		
		Dim testLine: testLine = Array(Plane(0), Rhino.PointAdd(Plane(0),Plane(1)))
		Dim Pt1:	Pt1 = Rhino.LineClosestPoint(TestLine,Rhino.BoundingBox(aOrderedObj(0), Plane)(1))
		Dim Pt2:	pt2 = Rhino.LineClosestPOint(TestLine,Rhino.BoundingBox(aOrderedObj(Bound), Plane)(0))
		
		'calculate the span
		span = qDistance(Pt1, Pt2)
		Space = (Span - ttl_length)/ bound
		
	End If
		
	Dim sObj, base,min
	'	DrawPlaneFrame Plane, 5
	
	Rhino.EnableRedraw False
	
	'Move the objects
	If BlnStyle = True Then 'Centers
		
		For i = 1 To bound-1
		
			Rhino.MoveObject aOrderedObj(i), aCen(i), Rhino.PointAdd(aCen(0),Rhino.VectorScale((Plane(1)), i*Space))
		Next
		
	Else 'gap
		
		'make a vector the length of the desired spacing
		Dim vec: vec  = Rhino.VectorScale(Plane(1), Space)
		
		'Move each middle object from its current Min point to the previous objects
		'max point plus the spacing vector
		For i = 1 To bound-1
		
			sobj = aOrderedObj(i)'current object
			
			'min point, projected to the direction line
			min = Rhino.LineClosestPoint(TestLine,Rhino.BoundingBox(sObj,Plane)(0))
			
			'Previous object's max point, projected to the direction line
			temp = Rhino.BoundingBox(aorderedObj(i-1),Plane)'previous object bb
			
			Base = 	Rhino.LineClosestPoint(TestLine,Temp(1))

			Rhino.MoveObject sObj , Min, Rhino.PointAdd(Base, vec)
		
		Next
		
	End If
	
	Rhino.EnableRedraw True
	
End Sub

Function OrderObjects(aObj, Plane)
	
	Dim Bound: Bound = UBound(aObj)
	Dim Vplane: Vplane = Rhino.RotatePlane(Plane,90,Plane(1))
	Dim  aBB, aCen
	aBB = Rhino.BoundingBox(aObj, Plane)
	Plane(0) = AveragePoints(Array(aBB(0), aBB(6)))

	ReDim aCen(Bound)

	Dim i, temp, tempBox
	
	Dim XForm: Xform = Rhino.XformRotation(Plane, Rhino.WorldXYPlane())
	Dim revXForm: revXform = Rhino.XformRotation( Rhino.WorldXYPlane(),Plane)
	
	For i = 0 To Bound
		
		tempBox = Rhino.BoundingBox(aObj(i), Plane)
		temp = AveragePoints(Array(tempBox(0), tempBox(6)))
		aCen(i) = Rhino.PointTransform( Rhino.PlaneClosestPoint(vplane,Rhino.PlaneClosestPoint(Plane,temp)),xform)
		
	Next
	
	Dim aOrderedCen: aOrderedCen = Rhino.SortPoints(aCen)
	
	
	If  UBound(aOrderedCen) <> Bound Then
		MsgBox " Some objects have the same center in the spacing direction - not handled yet"
		Exit Function
	End If
	
	Dim j, n, OrderedObj

	ReDim OrderedObj(Bound)
	
	For i = 0 To Bound
		For j = 0 To Bound
			If Rhino.PointCompare(aOrderedCen(i), aCen(j)) Then
				OrderedObj (n) = aObj(j)
				n = n + 1
			End If
		Next
	Next
	
	For i = 0 To Bound
		aOrderedCen(i) =Rhino.PointTransform (aOrderedCen(i),revXform)
	Next
	

	OrderObjects = Array(OrderedObj, aOrderedCen)
	
End Function

Function QDistance(aPtA,aPtB)
	QDistance = Sqr( (aPtA(0 )- aPtB(0))^2 + (aPtA(1)- aPtB(1))^2 + (aPtA(2) - aPtB(2))^2 )
End Function

Function WhereInArray(item,arr, intCase)
	'Finds the locaton of a string in an array of strings
	'if the result is -1 then the item does not
	'appear in tha array

	Dim sItem, n, i
	n = False
	WhereInArray = -1

		
	For i = 0 To UBound(arr)
			
		If intCase = 0 Then
			If arr(i) = Item Then
				
				WhereInArray = i
				n = True
				Exit For
		
				
			End If
			
		Else 
			
			If LCase(arr(i)) = LCase(Item) Then
				
				WhereInArray = i
				n = True
				Exit For
	
			End If
			
		End If
			
	Next
	

	If n = False Then WhereInArray = -1
	
End Function

Function AveragePoints(aPts)
	'Finds the average coordinates of an array
	'of points.

	Dim X, Y, Z
	Dim i
	
	X = 0
	Y = 0
	Z = 0

	For i=0 To UBound (aPts)
			
		'add all the X values
		X = X+aPts(i)(0)
	
		'add all th Y values
		Y = Y+aPts(i)(1)			
	
		'add all the Z values
		Z = Z+apts(i)(2)
	Next
	
	'Divide by the number of points to
	'get the average  for each
	'create the output array from the 3 averages
	AveragePoints  =Array(X/(UBound(aPts)+1), Y/(UBound(aPts)+1), Z/(UBound(aPts)+1))

End Function

Function GetPlaneFromDirection()'To Do
	
	Dim aPts: aPts = Rhino.GetPoints(True,True,"First direction point.", "Second dimrection point.",2)
	If Not IsArray(aPts) Then Exit Function
	
	Dim vecDir: vecDir = Rhino.VectorCreate(apts(1), aPts(0))
	Dim crntPLane: crntPlane = Rhino.ViewCPlane()
	crntPLane(0) = apts(0)
	Dim vecY: vecY = Rhino.VectorRotate(vecDir,90,crntPlane(3))
	GetPlaneFromDirection = Rhino.PlaneFromFrame(aPts(0), Rhino.VectorUnitize(vecDir), Rhino.VectorUnitize(vecY))
	
	
End Function

Sub DrawPlaneFrame (aPlane, dblScale)
	'For testing
	Rhino.EnableRedraw(False)
	
	Dim pt0: Pt0 =aPlane(0)
	Dim aLines(5)
	
	Dim vec1: vec1 = Rhino.VectorScale(aPlane(1),dblScale)
	Dim pt1: Pt1 = Rhino.PointAdd (Pt0,vec1)
	Dim Pt4: Pt4 = Rhino.PointAdd (Pt0,Rhino.VectorReverse(Vec1))

	Dim vec2: vec2 = Rhino.VectorScale(aPlane(2),dblScale)
	Dim pt2: Pt2 = Rhino.PointAdd (Pt0,Vec2)	
	Dim Pt5: Pt5 = Rhino.PointAdd (Pt0,Rhino.VectorReverse(Vec2))
	Dim vec3: vec3 = Rhino.VectorScale(aPlane(3),dblScale)
	Dim pt3: Pt3 = Rhino.PointAdd (Pt0,Vec3)	
	Dim Pt6: Pt6 = Rhino.PointAdd (Pt0,Rhino.VectorReverse(Vec3))
	
	aLines(0) = Rhino.AddLine (Pt0,Pt1)
	aLines(1) = Rhino.AddLine (Pt0,pt2)
	aLines(2) =	Rhino.AddLine (Pt0,Pt3)
	aLines(3) = Rhino.AddLine (Pt0,Pt4)
	aLines(4) = Rhino.AddLine (Pt0,Pt5)
	aLines(5) = Rhino.AddLine (Pt0,Pt6)
	
	Rhino.ObjectColor Array(alines(0),alines(3)), vbRed
	Rhino.ObjectColor Array(alines(1),alines(4)), vbGreen
	Rhino.ObjectColor Array(alines(2),alines(5)), vbBlue
	
	Dim i
	For i = 0 To 2
		Rhino.CurveArrows aLines(i),2
	Next
			
	Dim sgrp: sGrp = Rhino.AddGroup
	
	Rhino.AddObjectsToGroup aLines,sGrp
	Rhino.EnableRedraw(True)
	
End Sub
