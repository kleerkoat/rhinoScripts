Option Explicit

'Rhino.AddStartupScript Rhino.LastLoadedScriptFile
'Rhino.AddAlias "BBToOrigin","_-Runscript (BBToOrigin)"



Private OldProj

If isEmpty(OldProj) then
	OldProj = "Yes"
End If

Sub BBToOrigin()
	  
	dim arrObj: arrObj = Rhino.GetObjects("Select objects to move.",,True, True)
	If not IsArray(arrObj) then exit sub
	
	Dim sProj: sProj = Rhino.GetString("Project move to Cplane?",OldProj,array("Yes","No"))
	If isNull(sProj) then exit sub
	
	If lCase(sProj) = "yes" then 
		sProj="Yes"
	ElseIf lCase(sProj) = "no" then
		sProj = "No"
	Else 
		Exit sub
	End If
	OldProj = SProj

	dim arrBB: arrBB = Rhino.BoundingBox(arrObj,Rhino.CurrentView())
	If IsArray(arrBB) Then
		dim aCen
		if sProj = "Yes" then
			aCen = Rhino.PlaneClosestPoint(Rhino.ViewCPlane,AveragePoints(arrBB))
		Else
			aCen = AveragePoints(arrBB)
		End if
	
		Rhino.MoveObjects arrObj, aCen, Rhino.ViewCPlane()(0)
        
	End If
          
End Sub

Function AveragePoints(arrPts)
	'Finds the average location of an array
	'of points.

	Dim X, Y, Z
	Dim i
	
	X = 0
	Y = 0
	Z = 0

	For i=0 To UBound (arrPts)
			
		'add all the X values
		X = X+arrPts(i)(0)
	
		'add all th Y values
		Y = Y+arrPts(i)(1)			
	
		'add all the Z values
		Z = Z+arrpts(i)(2)
	Next
	
	'Divide by the number of points to
	'get the average  for each
	'create the output array from the 3 averages
	AveragePoints  =array(X/(UBound(arrPts)+1), Y/(UBound(arrPts)+1), Z/(UBound(arrPts)+1))

End Function
