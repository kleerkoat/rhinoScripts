' script for Rhinoceros - select objects with object notes
Option Explicit

Sub SelObjWithNotes
Dim arrObjects, StrObject, count, StrValue

arrObjects = Rhino.NormalObjects
If Not IsArray(arrObjects) Then Rhino.Print "Create or unlock some objects !" : Exit Sub

Rhino.UnselectAllObjects

' search
count = 0
For Each StrObject In arrObjects
	If Rhino.IsObjectData(StrObject) Then
		StrValue = Rhino.GetObjectData(strObject, "ObjectNotes", "Text")
		If Not IsNull(StrValue) Then
			Rhino.SelectObject StrObject
			count = count + 1
		End If
	End If
Next

' return
If count = 0 Then
	Rhino.Print "No objects found with notes attached."
ElseIf count = 1 Then
	Rhino.Print "Selected one object with notes."
ElseIf count > 1 Then
	Rhino.Print "Selected " & count & " objects with notes."
End If

End Sub
'SelObjWithNotes
