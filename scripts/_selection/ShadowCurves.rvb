Option Explicit
'Script written by <insert name>
'Script copyrighted by <insert company name>
'Script version Thursday, February 03, 2011


'Rhino.AddStartupScript Rhino.LastLoadedScriptFile
'Rhino.AddAlias "ShadowCurves", "_-Runscript (ShadowCurves)"

'Call ShadowCurves()
Sub ShadowCurves()

	Dim aObj: aObj = Rhino.GetObjects("Select objects for shadows.", 8 + 16 + 32,, True)
	If Not isArray(aObj) Then Exit Sub
	Dim crntVName: crntVname = Rhino.CurrentView()
	
	Dim aPt: aPt = Rhino.GetPoint("Set light direction base point")
	If Not isArray(aPt) Then Exit Sub

	Dim crntView: crntView = Rhino.CurrentView()
	Dim lens: lens = Rhino.ViewCameraLens(crntView)
	Dim proj: proj = Rhino.ViewProjection(crntView)
	Dim CrntPlane: crntPlane = Rhino.ViewCPlane()
	Dim aDir(1)
	aDir(0) = apt
	aDir(1) = Rhino.GetPoint("Set light direction.", aPt)
	If Not isArray(aDir(1)) Then Exit Sub

	Dim sCrntView: sCrntView = Rhino.AddNamedView("crntView", Rhino.CurrentView())
	
	Rhino.EnableRedraw False
	
	Rhino.ViewProjection , 1
	Rhino.ViewCameraTarget , apt, Rhino.PointAdd(apt, Rhino.VectorUnitize(Rhino.VectorCreate(aDir(1), aDir(0))))

	'DrawPLaneFrame PLane, 10

	Rhino.ZoomSelected()
	Dim plane: Plane = Rhino.ViewCameraPlane()
	Dim aCorn: aCorn = Rhino.ViewNearCorners()
	
	Dim apts(3), i
	For i = 0 To 3
		aPts(i) = Rhino.LinePlaneIntersection(array(aCorn(i), Rhino.PointAdd(aCorn(i), PLane(3))), CrntPlane)	
	Next
	Dim sObj
	Rhino.UnselectAllObjects()
	For Each sobj In aobj
		If Not Rhino.IsMesh(sobj) Then
			Rhino.SelectObject sObj
		End If
		
	Next
	If isArray(Rhino.SelectedObjects()) Then Rhino.Command "_Silhouette", False
	
	If Rhino.LastCommandResult() = 0 Then
		Dim alastBrep: aLastBrep = Rhino.LastCreatedObjects()
	End If
	
	Rhino.UnselectAllObjects()
	For Each sobj In aobj
		If  Rhino.IsMesh(sobj) Then
			Rhino.SelectObject sObj
		End If
		
	Next
	Dim aLast
	If isArray(Rhino.SelectedObjects()) Then 
		Rhino.Command "_MeshOutline", False
	
		If Rhino.LastCommandResult() = 0 Then
			If isArray(alastBrep) Then 
				aLast = Rhino.JoinArrays(aLastBrep, Rhino.LastCreatedObjects())
			Else
				alast = Rhino.LastCreatedObjects()
				Dim alastMesh: aLastMesh = Rhino.LastCreatedObjects()
			End If
		End If
	End If
	
	
	If Not isArray(alast) Then
		If isArray(aLastBrep) Then
			alast = aLastBrep
		End If
			
	End If

	Dim starg: starg = Rhino.AddSrfPt(aPts)
	
	Dim aProj2: aProj2 = Rhino.ProjectCurveToSurface(aLast, starg, PLane(3))
	Rhino.DeleteObjects aLast
	Rhino.DeleteObject starg
	
	If isArray(aProj2) Then
		Rhino.SelectObjects aProj2
		
		Rhino.AddObjectsToGroup aProj2, Rhino.AddGroup
	
		Dim aBB: aBB = Rhino.BoundingBox(aProj2)
	
		Dim cbPt: cbPt = Rhino.PointAdd(aBB(2), Rhino.VectorCreate(aBB(2), abb(0)))
	
		Rhino.Command "_CurveBoolean _DeleteInput=_None " & Rhino.Pt2Str(cbPt, , True) & "_Enter", False
		If Rhino.LastCommandResult = 0 Then
			alast = Rhino.LastCreatedObjects()
			Rhino.UnselectAllObjects()
			Rhino.SelectObjects alast
		End If
	
	End If
	
	Rhino.RestoreNamedView sCrntView, crntView, True
	Rhino.DeleteNamedView crntView	
	Rhino.RenameView Rhino.CurrentView(), crntVName

	Rhino.EnableRedraw True
	
End Sub


Function AveragePoints(aPts)
	'Finds the average coordinates of an array
	'of points.

	Dim X, Y, Z
	Dim i
	
	X = 0
	Y = 0
	Z = 0

	For i=0 To UBound(aPts)
			
		'add all the X values
		X = X + aPts(i)(0)
	
		'add all th Y values
		Y = Y + aPts(i)(1)			
	
		'add all the Z values
		Z = Z + apts(i)(2)
	Next
	
	'Divide by the number of points to
	'get the average  for each
	'create the output array from the 3 averages
	AveragePoints = array(X / (UBound(aPts) + 1), Y / (UBound(aPts) + 1), Z / (UBound(aPts) + 1))

End Function
