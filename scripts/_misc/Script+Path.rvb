'////////////////////////////////////////

Function Pattern04()

Dim x, y, z

Dim arrPatt(),arrpatt2()
Dim i, t, d, e, f


i=0

For t = 0 To 80 Step .5

  
                    
'0  
    Z= 0
    y= 0+1*Sin((t-12)/2)
    x= (2.5*t)
    ReDim Preserve arrPatt(i)
    arrPatt(i) = Array(x,y,z)
    i = i+1
'1
    Z= 8-2*Cos((t)/4)
    y= 0+4*Sin((t)/4)
    x= (2.5*t)
    ReDim Preserve arrPatt(i)
    arrPatt(i) =Array(x,y,z)
    i = i+1
'2    
    Z= 9+2*Cos((t)/4)
    y= 4+3*Sin((t)/4)
    x= (2.5*t)
    ReDim Preserve arrPatt(i)
    arrPatt(i) = Array(x,y,z)
    i = i+1
'3    
    Z= 8+3*Sin((t)/4)
    y= 12+2*Cos((t)/2)
    x= (2.5*t)
    ReDim Preserve arrPatt(i)
    arrPatt(i) = Array(x,y,z)
    i = i+1
   
'4  
    z= 0
    y= 9-2*Cos((t+15)/8)
    x= (2.5*t)
    ReDim Preserve arrPatt(i)
    arrPatt(i) =Array(x,y,z)
    i = i+1


Next
 d=0

For f = 0 To 80
  
  For e = 0 To 4
    ReDim Preserve Arrpatt2(e)
    arrpatt2(e)=arrpatt(d)
    d=d+1

  Next
  
  Rhino.addpolyline arrpatt2
	

Next

End Function



pattern04()
