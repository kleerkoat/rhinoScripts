Option Explicit
'Script written by Ryan Gilmore
'Script version Monday, May 21, 2012 10:51:36 AM

'Call ChangeColorByLayer()
Sub ChangeColorByLayer()
	Dim arrObjects,strObjects
	arrObjects = Rhino.GetObjects("Select objects", 0, True, True)
	If IsArray(arrObjects) Then
		Rhino.EnableRedraw False
		For Each strObject In arrObjects
			Rhino.ObjectColorSource strObject, 0
		Next
		Rhino.EnableRedraw True
		Erase arrObjects
	End If
	
End Sub
