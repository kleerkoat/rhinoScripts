Option Explicit

'Call PopUpCPlaneViews

Sub PopUpCPlaneViews

	Dim arrItems(5), arrModes(5), intResult
	
	arrItems(0) = "Top"    : arrModes(0) = 0 ' item 0
	arrItems(1) = "Bottom"     : arrModes(1) = 0 ' item 1
	arrItems(2) = "Front"     : arrModes(2) = 0 ' item 1
	arrItems(3) = "Back"     : arrModes(3) = 0 ' item 1
	arrItems(4) = "Right"    : arrModes(4) = 0 ' item 2
	arrItems(5) = "Left"    : arrModes(5) = 0 ' item 2

	

	intResult = Rhino.PopupMenu(arrItems, arrModes)
	If (intResult = 0) Then
		Rhino.Command "'_SetView _CPlane _Top _Enter"
	ElseIf (intResult = 1) Then
		Rhino.Command "'_SetView _CPlane _Bottom _Enter"
	ElseIf (intResult = 2) Then
		Rhino.Command "'_SetView _CPlane _Front _Enter"
	ElseIf (intResult = 3) Then
		Rhino.Command "'_SetView _CPlane _Back _Enter"
	ElseIf (intResult = 4) Then
		Rhino.Command "'_SetView _CPlane _Right _Enter"
	ElseIf (intResult = 5) Then
		Rhino.Command "'_SetView _CPlane _Left _Enter"


	End If
	
End Sub
