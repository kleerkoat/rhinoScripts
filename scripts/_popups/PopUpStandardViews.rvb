Sub PopUpStandardViews

	Dim arrItems(6), arrModes(6), intResult
	
	arrItems(0) = "Top"    : arrModes(0) = 0 ' item 0
	arrItems(1) = "Bottom"     : arrModes(1) = 0 ' item 1
	arrItems(2) = "Front"     : arrModes(2) = 0 ' item 1
	arrItems(3) = "Back"     : arrModes(3) = 0 ' item 1
	arrItems(4) = "Right"    : arrModes(4) = 0 ' item 2
	arrItems(5) = "Left"    : arrModes(5) = 0 ' item 2
	arrItems(6) = "Perspective"    : arrModes(6) = 0 ' item 2
	

	intResult = Rhino.PopupMenu(arrItems, arrModes)
	If (intResult = 0) Then
	Rhino.Command "'_SetView _World _Top _Enter"
	ElseIf (intResult = 1) Then
		Rhino.Command "'_SetView _World _Bottom _Enter"
	ElseIf (intResult = 2) Then
		Rhino.Command "'_Setview _World _Front _Enter"
	ElseIf (intResult = 3) Then
		Rhino.Command "'_Setview _World _Back _Enter"
        ElseIf (intResult = 4) Then
		Rhino.Command "'_Setview _World _Right _Enter"
	ElseIf (intResult = 5) Then
		Rhino.Command "'_Setview _World _Left _Enter"
	ElseIf (intResult = 6) Then
		Rhino.Command "'_CPlane _World _top _Setview _World _perspective _Enter"

	end if
		End Sub

    
'Rhino.AddStartUpScript Rhino.LastLoadedScriptFile
'Rhino.AddAlias "PopUpViews", "_noEcho _-Runscript (PopUpStandardViews)"
